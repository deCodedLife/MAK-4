-- PROMSD-MAK4 { iso org(3) dod(6) internet(1) private(4) enterprises(1) promsd(36032) }
--
-- Title: Mak4-Mib-110.mib
-- OOO Promsviazdiazain
-- All Rights Reserved.
--
--
-- Last Edit: 05.10.2022 by Maxim Krakovskiy
-- Last Edit: 28.09.2023 by Anton Bachurin
--

PROMSD-MAK4 DEFINITIONS ::= BEGIN

	IMPORTS
		MODULE-IDENTITY, OBJECT-TYPE, NOTIFICATION-TYPE, IpAddress, enterprises		FROM SNMPv2-SMI
		TEXTUAL-CONVENTION							FROM SNMPv2-TC;

	promSD  MODULE-IDENTITY
		LAST-UPDATED  "202309130000Z"
		
		ORGANIZATION  "OOO Promsviazdizain"
		CONTACT-INFO  "Maxim Krakovskiy
			Postal: 
			Tel:       +7495-947-09-69
			Fax:       +7495-947-09-69
			E-mail:    office@promsd.ru"


	DESCRIPTION   "MIB module of PROMSD PDU with controller MAK-4v2. Only for build MAK-4 4-4.1.3 or higher"

    REVISION     "202309130000Z"
	DESCRIPTION "Fixed Syntax"

    REVISION     "202210050000Z"
	DESCRIPTION "Added psSettings branch"
	
	REVISION     "202105240000Z"
	DESCRIPTION "Fixed Systax"

    REVISION      "201607010000Z"
    DESCRIPTION "Added events 120..124"

	                                        
	::= {enterprises 36032}

	psMAK4 OBJECT IDENTIFIER ::= {promSD 1}

	psCommon OBJECT IDENTIFIER ::= {psMAK4 1}
	psEvents OBJECT IDENTIFIER ::= {psMAK4 2}
	psLoad OBJECT IDENTIFIER ::= {psMAK4 3}
	psBattery OBJECT IDENTIFIER ::= {psMAK4 4}
	psContactors OBJECT IDENTIFIER ::= {psMAK4 5}
	psVbvs OBJECT IDENTIFIER ::= {psMAK4 6}
	psMains OBJECT IDENTIFIER ::= {psMAK4 7}
	psTemperature OBJECT IDENTIFIER ::= {psMAK4 8}
	psSwitches OBJECT IDENTIFIER ::= {psMAK4 9}
	
	psSettings OBJECT IDENTIFIER ::= {psMAK4 10}
		psCommonSetting OBJECT IDENTIFIER ::= {psSettings 1}
		psAlarmsMasks OBJECT IDENTIFIER ::= {psSettings 2}
		 psAlarms1Masks OBJECT IDENTIFIER ::= {psAlarmsMasks 1}
		 psAlarms2Masks OBJECT IDENTIFIER ::= {psAlarmsMasks 2}
		 psRelay1Masks OBJECT IDENTIFIER ::= {psAlarmsMasks 3}
		 psRelay2Masks OBJECT IDENTIFIER ::= {psAlarmsMasks 4}
		 psRelay3Masks OBJECT IDENTIFIER ::= {psAlarmsMasks 5}
		 psRelay4Masks OBJECT IDENTIFIER ::= {psAlarmsMasks 6}
		psBatterySettings OBJECT IDENTIFIER ::= {psSettings 3}
        psBatteryShortTestSettings OBJECT IDENTIFIER ::= {psSettings 4}
		psContactorSettings OBJECT IDENTIFIER ::= {psSettings 5}
		psMainsSettings OBJECT IDENTIFIER ::= {psSettings 6}
		psTemperatureSettings OBJECT IDENTIFIER ::= {psSettings 7}
		psConfiguration OBJECT IDENTIFIER ::= {psSettings 8}
		psNetworkSettings OBJECT IDENTIFIER ::= {psSettings 9}
		psSecuritySettings OBJECT IDENTIFIER ::= {psSettings 10}
		psSNMPSettings OBJECT IDENTIFIER ::= {psSettings 11}

    psBMS OBJECT IDENTIFIER ::= {psMAK4 11}


--COMMON

	psSerial OBJECT-TYPE
	SYNTAX			INTEGER
	MAX-ACCESS		read-only
	STATUS			current
	DESCRIPTION		"Power supply serial number."
	::= {psCommon 1}

	psDescription OBJECT-TYPE
	SYNTAX			OCTET STRING (SIZE (0..9))
	MAX-ACCESS		read-only
	STATUS			current
	DESCRIPTION		"Power supply textural description in windows-1251."
	::= {psCommon 2}

	psFWRevision OBJECT-TYPE
	SYNTAX			INTEGER
	MAX-ACCESS		read-only
	STATUS			current
	DESCRIPTION		"MAK-4 firmWare revision. For revision A.B.C the returned value would be A * 100 + B * 10 + C."
	::= {psCommon 3}

	psTime OBJECT-TYPE
	SYNTAX			OCTET STRING (SIZE (14))
	MAX-ACCESS		read-write
	STATUS			current
	DESCRIPTION		"Current MAK-4 UTC time in format DDMMYYYYhhmmss"
	::= {psCommon 4}

--EVENTS

	EVENT ::= TEXTUAL-CONVENTION
	STATUS			current
	DESCRIPTION
          "Codes of power supply events processing by controller MAK-4."
	SYNTAX  INTEGER
	{
		internal-error(0),

		load-undervoltage(32),
		load-overvoltage(33),
		termocomensation(34),
		load-fuse-1-off(35),
		load-fuse-2-off(36),
		load-fuse-3-off(37),
		load-fuse-4-off(38),
		load-fuse-5-off(39),
		load-fuse-6-off(40),
		load-fuse-7-off(41),
		load-fuse-8-off(42),
		load-fuse-9-off(43),
		load-fuse-10-off(44),
		load-fuse-11-off(45),
		load-fuse-12-off(46),
		load-fuse-13-off(47),
		load-fuse-14-off(48),
		load-fuse-15-off(49),
		load-fuse-16-off(50),
		load-fuse-17-off(51),
		load-fuse-18-off(52),
		load-fuse-19-off(53),
		load-fuse-20-off(54),
		load-fuse-21-off(55),
		load-fuse-22-off(56),
		load-fuse-23-off(57),
		load-fuse-24-off(58),
		load-fuse-25-off(59),
		load-fuse-26-off(60),
		load-fuse-27-off(61),
		load-fuse-28-off(62),
		load-fuse-29-off(63),
		load-fuse-30-off(64),
		load-fuse-31-off(65),
		load-fuse-32-off(66),
		load-fuse-33-off(67),
		load-fuse-34-off(68),
		load-fuse-35-off(69),
		load-fuse-36-off(70),
		load-fuse-37-off(71),
		load-fuse-38-off(72),
		load-fuse-39-off(73),
		load-fuse-40-off(74),
		load-fuse-41-off(75),
		load-fuse-42-off(76),
		load-fuse-43-off(77),
		load-fuse-44-off(78),
		load-fuse-45-off(79),
		load-fuse-46-off(80),
		load-fuse-47-off(81),
		load-fuse-48-off(82),
		load-fuse-49-off(83),
		load-fuse-50-off(84),
		load-fuse-51-off(85),
		load-fuse-52-off(86),
		ukdv-error(87),

		battery-discharge(96),
		low-battety(97),
		battery-charge(98),
		battery-fast-chrge(99),
		battery-floating(100),
		battery-equalizing-charge(101),
		battery-test(102),
		battery-fuse-1-off(103),
		battery-fuse-2-off(104),
		battery-fuse-3-off(105),
		battery-fuse-4-off(106),
		battery-fuse-5-off(107),
		battery-fuse-6-off(108),
		battery-fuse-7-off(109),
		battery-fuse-8-off(110),
		group-1-block-alarm(111),
		group-2-block-alarm(112),
		group-3-block-alarm(113),
		group-4-block-alarm(114),
		group-5-block-alarm(115),
		group-6-block-alarm(116),
		group-7-block-alarm(117),
		group-8-block-alarm(118),
		upkb-error(119),
		icharge-less-1A(120),
		icharge-less-2A(121),
		icharge-less-3A(122),
		icharge-less-4A(123),
		icharge-less-5A(124),
		battery-overheat(125),
		battery-short-test(126),
		battery-short-test-fail(127),

		contactor-1-off(128),
		contactor-2-off(129),
		contactor-3-off(130),
		contactor-4-off(131),
		contactor-1-alarm(132),
		contactor-2-alarm(133),
		contactor-3-alarm(134),
		contactor-4-alarm(135),

		vbv-1-alarm(160),
		vbv-2-alarm(161),
		vbv-3-alarm(162),
		vbv-4-alarm(163),
		vbv-5-alarm(164),
		vbv-6-alarm(165),
		vbv-7-alarm(166),
		vbv-8-alarm(167),
		vbv-9-alarm(168),
		vbv-10-alarm(169),
		vbv-11-alarm(170),
		vbv-12-alarm(171),
		vbv-13-alarm(172),
		vbv-14-alarm(173),
		vbv-15-alarm(174),
		vbv-16-alarm(175),
		vbv-17-alarm(176),
		vbv-18-alarm(177),
		vbv-19-alarm(178),
		vbv-20-alarm(179),
		vbv-21-alarm(180),
		vbv-22-alarm(181),
		vbv-23-alarm(182),
		vbv-24-alarm(183),
		vbv-25-alarm(184),
		vbv-26-alarm(185),
		vbv-27-alarm(186),
		vbv-28-alarm(187),
		vbv-29-alarm(188),
		vbv-30-alarm(189),
		vbv-31-alarm(190),
		vbv-32-alarm(191),
		vbv-33-alarm(192),
		vbv-34-alarm(193),
		vbv-35-alarm(194),
		vbv-36-alarm(195),
		vbv-37-alarm(196),
		vbv-38-alarm(197),
		vbv-39-alarm(198),
		vbv-40-alarm(199),
		vbv-41-alarm(200),
		vbv-42-alarm(201),
		vbv-43-alarm(202),
		vbv-44-alarm(203),
		vbv-45-alarm(204),
		vbv-46-alarm(205),
		vbv-47-alarm(206),
		vbv-48-alarm(207),
		vbv-49-alarm(208),
		vbv-50-alarm(209),
		vbv-51-alarm(210),
		vbv-52-alarm(211),
		vbv-53-alarm(212),
		vbv-54-alarm(213),
		vbv-55-alarm(214),
		vbv-56-alarm(215),
		vbv-57-alarm(216),
		vbv-58-alarm(217),
		vbv-59-alarm(218),
		vbv-60-alarm(219),
		vbv-61-alarm(220),
		vbv-62-alarm(221),
		vbv-63-alarm(222),
		vbv-64-alarm(223),
		vbv-65-alarm(224),
		vbv-66-alarm(225),
		vbv-67-alarm(226),
		vbv-68-alarm(227),
		vbv-69-alarm(228),
		vbv-70-alarm(229),
		vbv-71-alarm(230),
		vbv-72-alarm(231),
		vbv-73-alarm(232),
		vbv-74-alarm(233),
		vbv-75-alarm(234),
		vbv-76-alarm(235),
		vbv-77-alarm(236),
		vbv-78-alarm(237),
		vbv-79-alarm(238),
		vbv-80-alarm(239),
		vbv-81-alarm(240),
		vbv-82-alarm(241),
		vbv-83-alarm(242),
		vbv-84-alarm(243),
		vbv-85-alarm(244),
		vbv-86-alarm(245),
		vbv-87-alarm(246),
		vbv-88-alarm(247),
		vbv-89-alarm(248),
		vbv-90-alarm(249),
		vbv-91-alarm(250),
		vbv-92-alarm(251),
		vbv-93-alarm(252),
		vbv-94-alarm(253),
		vbv-95-alarm(254),
		vbv-96-alarm(255),
		vbv-97-alarm(256),
		vbv-98-alarm(257),
		vbv-99-alarm(258),
		vbv-100-alarm(259),
		vbv-101-alarm(260),
		vbv-102-alarm(261),
		vbv-103-alarm(262),
		vbv-104-alarm(263),
		vbv-105-alarm(264),
		vbv-106-alarm(265),
		vbv-107-alarm(266),
		vbv-108-alarm(267),
		vbv-109-alarm(268),
		vbv-110-alarm(269),
		vbv-111-alarm(270),
		vbv-112-alarm(271),
		vbv-113-alarm(272),
		vbv-114-alarm(273),
		vbv-115-alarm(274),
		vbv-116-alarm(275),
		vbv-117-alarm(276),
		vbv-118-alarm(277),
		vbv-119-alarm(278),
		vbv-120-alarm(279),
		vbv-121-alarm(280),
		vbv-122-alarm(281),
		vbv-123-alarm(282),
		vbv-124-alarm(283),
		vbv-125-alarm(284),
		vbv-126-alarm(285),
		vbv-127-alarm(286),
		vbv-128-alarm(287),
		vbv-129-alarm(288),
		vbv-130-alarm(289),
		vbv-131-alarm(290),
		vbv-132-alarm(291),
		vbv-133-alarm(292),
		vbv-134-alarm(293),
		vbv-135-alarm(294),
		vbv-136-alarm(295),
		vbv-137-alarm(296),
		vbv-138-alarm(297),
		vbv-139-alarm(298),
		vbv-140-alarm(299),
		vbv-141-alarm(300),
		vbv-142-alarm(301),
		vbv-143-alarm(302),
		vbv-144-alarm(303),
		vbv-145-alarm(304),
		vbv-146-alarm(305),
		vbv-147-alarm(306),
		vbv-148-alarm(307),
		vbv-149-alarm(308),
		vbv-150-alarm(309),
		vbv-151-alarm(310),
		vbv-152-alarm(311),
		vbv-153-alarm(312),
		vbv-154-alarm(313),
		vbv-155-alarm(314),
		vbv-156-alarm(315),
		vbv-157-alarm(316),
		vbv-158-alarm(317),
		vbv-159-alarm(318),
		vbv-160-alarm(319),
		vbv-161-alarm(320),
		vbv-162-alarm(321),
		vbv-163-alarm(322),
		vbv-164-alarm(323),
		vbv-165-alarm(324),
		vbv-166-alarm(325),
		vbv-167-alarm(326),
		vbv-168-alarm(327),
		vbv-169-alarm(328),
		vbv-170-alarm(329),
		vbv-171-alarm(330),
		vbv-172-alarm(331),
		vbv-173-alarm(332),
		vbv-174-alarm(333),
		vbv-175-alarm(334),
		vbv-176-alarm(335),
		vbv-177-alarm(336),
		vbv-178-alarm(337),
		vbv-179-alarm(338),
		vbv-180-alarm(339),
		vbv-no-reverve(340),
		vbv-high-efficiency(341),

		line-1-alarm(352),
		line-2-alarm(353),
		line-3-alarm(354),
		mains-error(355),
		light-protection-alarm(356),

		low-temperature-2(384),
		high-temperature-2(385),
		temperature-error(386),

		switch-1-alarm(416),
		switch-2-alarm(417),
		switch-3-alarm(418),
		switch-4-alarm(419),
		switch-5-alarm(420),
		switch-6-alarm(421),
		switch-7-alarm(422),
		switch-8-alarm(423),
		switch-9-alarm(424),
		switch-10-alarm(425),
		switch-11-alarm(426),
		switch-12-alarm(427),
		switch-13-alarm(428),
		switch-14-alarm(429),
		switch-15-alarm(430),
		switch-16-alarm(431),

        li-ion-alarm(480),
        li-ion-com-fail(481),

		boot(512),
		settings-save(513),
		clock-set(514),
		battery-test-start(515),
		equalizing-charge-start(516),
		battery-shortt-test-start(517)
	}



	psAlarm1Table OBJECT-TYPE
	SYNTAX			SEQUENCE OF PSAlarm1Entry
	MAX-ACCESS		not-accessible
	STATUS			current
	DESCRIPTION		"Table of 1st urgency alarms. Events are returned in order of there code numbers, but not the time when they are happened."
	::= {psEvents 1}

	psAlarm1Entry OBJECT-TYPE
	SYNTAX			PSAlarm1Entry
	MAX-ACCESS		not-accessible
	STATUS			current
	DESCRIPTION		""
	INDEX {psAlarm1Number}
	::= {psAlarm1Table 1}

	PSAlarm1Entry ::= SEQUENCE
	{
		psAlarm1Number		INTEGER,
		psAlarm1Event		INTEGER
	}

	psAlarm1Number OBJECT-TYPE
	SYNTAX			INTEGER (1..448)
	MAX-ACCESS		read-write
	STATUS			current
	DESCRIPTION		"1st urgency alarm number."
	::= {psAlarm1Entry 1}

	psAlarm1Event OBJECT-TYPE
	SYNTAX			EVENT
	MAX-ACCESS		read-write
	STATUS			current
	DESCRIPTION		"1st urgency alarm code."
	::= {psAlarm1Entry 2}

	psAlarm1AddedTrap NOTIFICATION-TYPE
	OBJECTS
	{
		psTime,
		psAlarm1Event
	}
	STATUS current
	DESCRIPTION "Trap of 1st urgency Alarm Added Event"
	::= {psEvents 2}


	psAlarm2Table OBJECT-TYPE
	SYNTAX			SEQUENCE OF PSAlarm2Entry
	MAX-ACCESS		not-accessible
	STATUS			current
	DESCRIPTION		"Table of 2nd urgency alarms. Events are returned in order of there code numbers, but not the time when they are happened."
	::= {psEvents 3}

	psAlarm2Entry OBJECT-TYPE
	SYNTAX			PSAlarm2Entry
	MAX-ACCESS		not-accessible
	STATUS			current
	DESCRIPTION		""
	INDEX {psAlarm2Number}
	::= {psAlarm2Table 1}

	PSAlarm2Entry ::= SEQUENCE
	{
		psAlarm2Number		INTEGER,
		psAlarm2Event		INTEGER
	}

	psAlarm2Number OBJECT-TYPE
	SYNTAX			INTEGER (1..448)
	MAX-ACCESS		read-only
	STATUS			current
	DESCRIPTION		"2nd urgency alarm number."
	::= {psAlarm2Entry 1}

	psAlarm2Event OBJECT-TYPE
	SYNTAX			EVENT
	MAX-ACCESS		read-only
	STATUS			current
	DESCRIPTION		"2nd urgency alarm code."
	::= {psAlarm2Entry 2}

	psAlarm2AddedTrap NOTIFICATION-TYPE
	OBJECTS
	{
		psTime,
		psAlarm2Event
	}
	STATUS current
	DESCRIPTION "Trap of 2nd urgency alarm Added event."
	::= {psEvents 4}

	psSignalRelayTable OBJECT-TYPE
	SYNTAX			SEQUENCE OF PSSignalRelayEntry
	MAX-ACCESS		not-accessible
	STATUS			current
	DESCRIPTION		"Table of event amounts of signal relais. If event amount is zero, corresponding signal relay coil is switched off, otherwise coil is switched on."
	::= {psEvents 5}

	psSignalRelayEntry OBJECT-TYPE
	SYNTAX			PSSignalRelayEntry
	MAX-ACCESS		not-accessible
	STATUS			current
	DESCRIPTION		""
	INDEX {psRelayNumber}
	::= {psSignalRelayTable 1}

	PSSignalRelayEntry ::= SEQUENCE
	{
		psRelayNumber		INTEGER,
		psRelayEventAmount	INTEGER
	}

	psRelayNumber OBJECT-TYPE
	SYNTAX			INTEGER (1..4)
	MAX-ACCESS		read-only
	STATUS			current
	DESCRIPTION		"Signal relay number."
	::= {psSignalRelayEntry 1}

	psRelayEventAmount OBJECT-TYPE
	SYNTAX			INTEGER (1..320)
	MAX-ACCESS		read-only
	STATUS			current
	DESCRIPTION		"Amount of active events for the signal relay."
	::= {psSignalRelayEntry 2}

	psJournalTable OBJECT-TYPE
	SYNTAX			SEQUENCE OF PSJournalEntry
	MAX-ACCESS		not-accessible
	STATUS			current
	DESCRIPTION		"Table of journal records. The oldest record has the first number."
	::= {psEvents 6}

	psJournalEntry OBJECT-TYPE
	SYNTAX			PSJournalEntry
	MAX-ACCESS		not-accessible
	STATUS			current
	DESCRIPTION		""
	INDEX {psJournalNumber}
	::= {psJournalTable 1}

	PSJournalEntry ::= SEQUENCE
	{
		psJournalNumber		INTEGER,
		psJournalTime		OCTET STRING,
		psJournalMode		INTEGER,
		psJournalEvent		INTEGER
	}

	psJournalNumber OBJECT-TYPE
	SYNTAX			INTEGER (1..2000)
	MAX-ACCESS		read-only
	STATUS			current
	DESCRIPTION		"Record number in journal."
	::= {psJournalEntry 1}


	psJournalTime OBJECT-TYPE
	SYNTAX			OCTET STRING (SIZE(14))
	MAX-ACCESS		read-only
	STATUS			current
	DESCRIPTION		"Event time (UTC) in format DDMMYYYYhhmmss."
	::= {psJournalEntry 2}


	psJournalMode OBJECT-TYPE
	SYNTAX			INTEGER {end(0), begin(1), happened(2), empty(3), error(4)}
	MAX-ACCESS		read-only
	STATUS			current
	DESCRIPTION		"Mode of event: begin / end / happening of event."
	::= {psJournalEntry 3}


	psJournalEvent OBJECT-TYPE
	SYNTAX			EVENT
	MAX-ACCESS		read-only
	STATUS			current
	DESCRIPTION		"Event code."
	::= {psJournalEntry 4}


	psAlarm1RemovedTrap NOTIFICATION-TYPE
	OBJECTS
	{
		psTime,
		--psAlarm1RemovedEvent
        psAlarm1Event
	}
	STATUS current
	DESCRIPTION "Trap of 1st urgency Alarm Removed Event"
	::= {psEvents 7}


	psAlarm2RemovedTrap NOTIFICATION-TYPE
	OBJECTS
	{
		psTime,
		--psAlarm2RemovedEvent
        psAlarm2Event
	}
	STATUS current
	DESCRIPTION "Trap of 2nd urgency Alarm Removed event."
	::= {psEvents 8}


--LOAD

	psLoadVoltage OBJECT-TYPE
	SYNTAX			INTEGER
	UNITS			"0.01V"
	MAX-ACCESS		read-only
	STATUS			current
	DESCRIPTION		"Load(output) voltage in 0.01V."
	::= {psLoad 1}

	psLoadCurrent OBJECT-TYPE
	SYNTAX			INTEGER
	UNITS			"0.001A"
	MAX-ACCESS		read-only
	STATUS			current
	DESCRIPTION		"Load(output) current in 0.001A."
	::= {psLoad 2}

	psLoadStatus OBJECT-TYPE
	SYNTAX			INTEGER {normal(0), thermocompensation(1), undervoltage(2), overvoltage(3), error(4)}
	MAX-ACCESS		read-only
	STATUS			current
	DESCRIPTION		"Status of load(output). If status is error(4) the values of psLoadVoltage and psLoadCurrent should be discarded."
	::= {psLoad 3}

	psLoadFuseTable OBJECT-TYPE
	SYNTAX			SEQUENCE OF PSLoadFuseEntry
	MAX-ACCESS		not-accessible
	STATUS			current
	DESCRIPTION		"Status of load(output) fuses."
	::= {psLoad 4}

	psLoadFuseEntry OBJECT-TYPE
	SYNTAX			PSLoadFuseEntry
	MAX-ACCESS		not-accessible
	STATUS			current
	DESCRIPTION		""
	INDEX {psLoadFuseNumber}
	::= {psLoadFuseTable 1}

	PSLoadFuseEntry ::= SEQUENCE
	{
		psLoadFuseNumber	INTEGER,
		psLoadFuseStatus	INTEGER
	}

	psLoadFuseNumber OBJECT-TYPE
	SYNTAX			INTEGER (1..52)
	MAX-ACCESS		read-only
	STATUS			current
	DESCRIPTION		"Load fuse number."
	::= {psLoadFuseEntry 1}

	psLoadFuseStatus OBJECT-TYPE
	SYNTAX			INTEGER {on(0), off(1), unknown(2), error(3)}
	MAX-ACCESS		read-only
	STATUS			current
	DESCRIPTION		"Load fuse status."
	::= {psLoadFuseEntry 2}


--Amperemeter
    psAmperemeterTable OBJECT-TYPE  
    SYNTAX			SEQUENCE OF PSAmperemeterEntry
	MAX-ACCESS		not-accessible
	STATUS			current
	DESCRIPTION		"status of Amperemeters"
	::= {psLoad 5} 

    psAmperemeterEntry OBJECT-TYPE
    SYNTAX			PSAmperemeterEntry
	MAX-ACCESS		not-accessible
	STATUS			current
	DESCRIPTION		""
	INDEX {psAmperemeterNumber}
	::= {psAmperemeterTable 1}

    PSAmperemeterEntry ::= SEQUENCE
	{
		psAmperemeterNumber		 INTEGER,
		psAmperemeterCurrent	 INTEGER,
		psAmperemeterStatus		 INTEGER
	}

    psAmperemeterNumber OBJECT-TYPE
	SYNTAX			INTEGER (1..16)
	MAX-ACCESS		read-only
	STATUS			current
	DESCRIPTION		"Amperemeter number."
	::= {psAmperemeterEntry 1}

    psAmperemeterCurrent OBJECT-TYPE
	SYNTAX			INTEGER
	UNITS			"0.001A"
	MAX-ACCESS		read-only
	STATUS			current
	DESCRIPTION		"Amperemeter current"
	::= {psAmperemeterEntry 2}

    psAmperemeterStatus OBJECT-TYPE
	SYNTAX			INTEGER {normal(0), alarm(1)}
	MAX-ACCESS		read-only
	STATUS			current
	DESCRIPTION		"Amperemeter status"
	::= {psAmperemeterEntry 3}



-- BATTERY

	psBatterySummCurrent OBJECT-TYPE
	SYNTAX			INTEGER
	UNITS			"0.001A"
	MAX-ACCESS		read-only
	STATUS			current
	DESCRIPTION		"Summary current of all connected battery groups in 0.001A."
	::= {psBattery 1}

	psBatteryStatus OBJECT-TYPE
	SYNTAX			INTEGER {charge(0), floating(1), fast-charge(2), equalizing-charge(3), discharge(4), low(5), test(6), absent(7), error(8)}
	MAX-ACCESS		read-only
	STATUS			current
	DESCRIPTION		"Battery status. If status is error(4) the value of psBatterySummCurrent should be discarded."
	::= {psBattery 2}

	psGroupTable OBJECT-TYPE
	SYNTAX			SEQUENCE OF PSGroupEntry
	MAX-ACCESS		not-accessible
	STATUS			current
	DESCRIPTION		"Status of battery groups."
	::= {psBattery 3}

	psGroupEntry OBJECT-TYPE
	SYNTAX			PSGroupEntry
	MAX-ACCESS		not-accessible
	STATUS			current
	DESCRIPTION		""
	INDEX {psGroupNumber}
	::= {psGroupTable 1}

	PSGroupEntry ::= SEQUENCE
	{
		psGroupNumber		INTEGER,
		psGroupVoltage		INTEGER,
		psGroupCurrent		INTEGER,
		psGroupFuseStatus	INTEGER,
		psGroupStatus		INTEGER
	}

	psGroupNumber OBJECT-TYPE
	SYNTAX			INTEGER (1..8)
	MAX-ACCESS		read-only
	STATUS			current
	DESCRIPTION		"Battery group number."
	::= {psGroupEntry 1}

	psGroupVoltage OBJECT-TYPE
	SYNTAX			INTEGER
	UNITS			"0.01V"
	MAX-ACCESS		read-only
	STATUS			current
	DESCRIPTION		"Battery group voltage in 0.01V."
	::= {psGroupEntry 2}

	psGroupCurrent OBJECT-TYPE
	SYNTAX			INTEGER
	UNITS			"0.001A"
	MAX-ACCESS		read-only
	STATUS			current
	DESCRIPTION		"Battery group current in 0.001A."
	::= {psGroupEntry 3}

	psGroupStatus OBJECT-TYPE
	SYNTAX			INTEGER {connected(0), disconnected(1), error(2)}
	MAX-ACCESS		read-only
	STATUS			current
	DESCRIPTION		"Battery group status. If status is error(2) the values of psGroupVoltage and psGroupCurrent should be discarded."
	::= {psGroupEntry 4}

	psGroupFuseStatus OBJECT-TYPE
	SYNTAX			INTEGER {on(0), off(1), unknown(2), error(3)}
	MAX-ACCESS		read-only
	STATUS			current
	DESCRIPTION		"Battery group fuse status."
	::= {psGroupEntry 5}

	psBlockTable OBJECT-TYPE
	SYNTAX			SEQUENCE OF PSBlockEntry
	MAX-ACCESS		not-accessible
	STATUS			current
	DESCRIPTION		"Status of battery group blocks (elements)."
	::= {psBattery 4}

	psBlockEntry OBJECT-TYPE
	SYNTAX			PSBlockEntry
	MAX-ACCESS		not-accessible
	STATUS			current
	DESCRIPTION		""
	INDEX			{psBlockGroup, psBlockNumber}
	::= {psBlockTable 1}

	PSBlockEntry ::= SEQUENCE
	{
		psBlockGroup		INTEGER,
		psBlockNumber		INTEGER,
		psBlockVoltage		INTEGER,
		psBlockTemperature	INTEGER,
		psBlockStatus		INTEGER
	}

	psBlockGroup OBJECT-TYPE
	SYNTAX			INTEGER (1..8)
	MAX-ACCESS		read-only
	STATUS			current
	DESCRIPTION		"Battery group number where the given block located in."
	::= {psBlockEntry 1}

	psBlockNumber OBJECT-TYPE
	SYNTAX			INTEGER (1..30)
	MAX-ACCESS		read-only
	STATUS			current
	DESCRIPTION		"Block number in battery group."
	::= {psBlockEntry 2}

	psBlockVoltage OBJECT-TYPE
	SYNTAX			INTEGER
	UNITS			"0.01V"
	MAX-ACCESS		read-only
	STATUS			current
	DESCRIPTION		"Battery group block voltage in 0.01V."
	::= {psBlockEntry 3}

	psBlockTemperature OBJECT-TYPE
	SYNTAX			INTEGER
	UNITS			"0.1degC"
	MAX-ACCESS		read-only
	STATUS			current
	DESCRIPTION		"Battery group block temperature in 0.01V."
	::= {psBlockEntry 4}

	psBlockStatus OBJECT-TYPE
	SYNTAX			INTEGER {normal(0), undervoltage(1), ovrevoltage(2), overheart(3), error(4)}
	MAX-ACCESS		read-only
	STATUS			current
	DESCRIPTION		"Battery group block status. If status is error(4) the values of psBlockVoltage and psBlockTemperature should be discarded."
	::= {psBlockEntry 5}

	psTestTable OBJECT-TYPE
	SYNTAX			SEQUENCE OF PSTestEntry
	MAX-ACCESS		not-accessible
	STATUS			current
	DESCRIPTION		"Results of battery tests."
	::= {psBattery 5}

	psTestEntry OBJECT-TYPE
	SYNTAX			PSTestEntry
	MAX-ACCESS		not-accessible
	STATUS			current
	DESCRIPTION		""
	INDEX			{psTestNumber}
	::= {psTestTable 1}

	PSTestEntry ::= SEQUENCE
	{
		psTestNumber		INTEGER,
		psTestStartTime		OCTET STRING,
		psTestResult		INTEGER,
		psTestLength		INTEGER,
		psTestCapacity		INTEGER,
		psTestFinalVoltage	INTEGER,
		psTestGroup1		INTEGER,
		psTestGroup2		INTEGER,
		psTestGroup3		INTEGER,
		psTestGroup4		INTEGER,
		psTestGroup5		INTEGER,
		psTestGroup6		INTEGER,
		psTestGroup7		INTEGER,
		psTestGroup8		INTEGER
	}

	psTestNumber OBJECT-TYPE
	SYNTAX			INTEGER (1..4)
	MAX-ACCESS		read-only
	STATUS			current
	DESCRIPTION		"Battery test number."
	::= {psTestEntry 1}

	psTestStartTime OBJECT-TYPE
	SYNTAX			OCTET STRING (SIZE (14))
	MAX-ACCESS		read-only
	STATUS			current
	DESCRIPTION		"Test start time (UTC) in format DDMMYYYYhhmmss."
	::= {psTestEntry 2}

	psTestResult OBJECT-TYPE
	SYNTAX			INTEGER {success(0), unknown(1), user-braked(2), low-current(3), go-charge(4), battery-off(5), timeout(6), mesure-error(7), empty(8), error(9)}
	MAX-ACCESS		read-only
	STATUS			current
	DESCRIPTION		"Battery test result."
	::= {psTestEntry 3}

	psTestLength OBJECT-TYPE
	SYNTAX			INTEGER
	UNITS			"sec"
	MAX-ACCESS		read-only
	STATUS			current
	DESCRIPTION		"Battery test duration in seconds."
	::= {psTestEntry 4}

	psTestCapacity OBJECT-TYPE
	SYNTAX			INTEGER
	UNITS			"0.001A * hour"
	MAX-ACCESS		read-only
	STATUS			current
	DESCRIPTION		"Battery test capacity in 0.001A * hour."
	::= {psTestEntry 5}

	psTestFinalVoltage OBJECT-TYPE
	SYNTAX			INTEGER
	UNITS			"0.01V"
	MAX-ACCESS		read-only
	STATUS			current
	DESCRIPTION		"Output voltage at the end of test in 0.01V."
	::= {psTestEntry 6}

	psTestGroup1 OBJECT-TYPE
	SYNTAX			INTEGER {disconnected(0), connected(1)}
	MAX-ACCESS		read-only
	STATUS			current
	DESCRIPTION		"Connection of group 1 while battery test."
	::= {psTestEntry 7}

	psTestGroup2 OBJECT-TYPE
	SYNTAX			INTEGER {disconnected(0), connected(1)}
	MAX-ACCESS		read-only
	STATUS			current
	DESCRIPTION		"Connection of group 2 while battery test."
	::= {psTestEntry 8}

	psTestGroup3 OBJECT-TYPE
	SYNTAX			INTEGER {disconnected(0), connected(1)}
	MAX-ACCESS		read-only
	STATUS			current
	DESCRIPTION		"Connection of group 3 while battery test."
	::= {psTestEntry 9}

	psTestGroup4 OBJECT-TYPE
	SYNTAX			INTEGER {disconnected(0), connected(1)}
	MAX-ACCESS		read-only
	STATUS			current
	DESCRIPTION		"Connection of group 4 while battery test."
	::= {psTestEntry 10}

	psTestGroup5 OBJECT-TYPE
	SYNTAX			INTEGER {disconnected(0), connected(1)}
	MAX-ACCESS		read-only
	STATUS			current
	DESCRIPTION		"Connection of group 5 while battery test."
	::= {psTestEntry 11}

	psTestGroup6 OBJECT-TYPE
	SYNTAX			INTEGER {disconnected(0), connected(1)}
	MAX-ACCESS		read-only
	STATUS			current
	DESCRIPTION		"Connection of group 6 while battery test."
	::= {psTestEntry 12}

	psTestGroup7 OBJECT-TYPE
	SYNTAX			INTEGER {disconnected(0), connected(1)}
	MAX-ACCESS		read-only
	STATUS			current
	DESCRIPTION		"Connection of group 7 while battery test."
	::= {psTestEntry 13}

	psTestGroup8 OBJECT-TYPE
	SYNTAX			INTEGER {disconnected(0), connected(1)}
	MAX-ACCESS		read-only
	STATUS			current
	DESCRIPTION		"Connection of group 8 while battery test."
	::= {psTestEntry 14}



--BEGIN----------------------------------------------------------------------------------------------
	psShortTestTable OBJECT-TYPE
	SYNTAX			SEQUENCE OF PSShortTestEntry
	MAX-ACCESS		not-accessible
	STATUS			current
	DESCRIPTION		"Results of battery tests."
	::= {psBattery 6}

	psShortTestEntry OBJECT-TYPE
	SYNTAX			PSShortTestEntry
	MAX-ACCESS		not-accessible
	STATUS			current
	DESCRIPTION		""
	INDEX			{psShortTestNumber}
	::= {psShortTestTable 1}

	PSShortTestEntry ::= SEQUENCE
	{
		psShortTestNumber		INTEGER,
		psShortTestStartTime		OCTET STRING,
		psShortTestResult		INTEGER,
		psShortTestLength		INTEGER,
		psShortTestCapacity		INTEGER,
		psShortTestFinalVoltage	INTEGER,
		psShortTestGroup1		INTEGER,
		psShortTestGroup2		INTEGER,
		psShortTestGroup3		INTEGER,
		psShortTestGroup4		INTEGER,
		psShortTestGroup5		INTEGER,
		psShortTestGroup6		INTEGER,
		psShortTestGroup7		INTEGER,
		psShortTestGroup8		INTEGER
	}

	psShortTestNumber OBJECT-TYPE
	SYNTAX			INTEGER (1..4)
	MAX-ACCESS		read-only
	STATUS			current
	DESCRIPTION		"Battery Short test number."
	::= {psShortTestEntry 1}

	psShortTestStartTime OBJECT-TYPE
	SYNTAX			OCTET STRING (SIZE (14))
	MAX-ACCESS		read-only
	STATUS			current
	DESCRIPTION		"Short Test start time (UTC) in format DDMMYYYYhhmmss."
	::= {psShortTestEntry 2}

	psShortTestResult OBJECT-TYPE
	SYNTAX			INTEGER {success(0), unknown(1), user-braked(2), low-current(3), go-charge(4), battery-off(5), timeout(6), mesure-error(7), empty(8), error(9), failed(11)}
	MAX-ACCESS		read-only
	STATUS			current
	DESCRIPTION		"Battery Short test result."
	::= {psShortTestEntry 3}

	psShortTestLength OBJECT-TYPE
	SYNTAX			INTEGER
	UNITS			"sec"
	MAX-ACCESS		read-only
	STATUS			current
	DESCRIPTION		"Battery Short test duration in seconds."
	::= {psShortTestEntry 4}

	psShortTestCapacity OBJECT-TYPE
	SYNTAX			INTEGER
	UNITS			"0.001A * hour"
	MAX-ACCESS		read-only
	STATUS			current
	DESCRIPTION		"Battery Short test capacity in 0.001A * hour."
	::= {psShortTestEntry 5}

	psShortTestFinalVoltage OBJECT-TYPE
	SYNTAX			INTEGER
	UNITS			"0.01V"
	MAX-ACCESS		read-only
	STATUS			current
	DESCRIPTION		"Output voltage at the end of test in 0.01V."
	::= {psShortTestEntry 6}

	psShortTestGroup1 OBJECT-TYPE
	SYNTAX			INTEGER {disconnected(0), connected(1)}
	MAX-ACCESS		read-only
	STATUS			current
	DESCRIPTION		"Connection of group 1 while battery Short test."
	::= {psShortTestEntry 7}

	psShortTestGroup2 OBJECT-TYPE
	SYNTAX			INTEGER {disconnected(0), connected(1)}
	MAX-ACCESS		read-only
	STATUS			current
	DESCRIPTION		"Connection of group 2 while battery Short test."
	::= {psShortTestEntry 8}

	psShortTestGroup3 OBJECT-TYPE
	SYNTAX			INTEGER {disconnected(0), connected(1)}
	MAX-ACCESS		read-only
	STATUS			current
	DESCRIPTION		"Connection of group 3 while battery Short test."
	::= {psShortTestEntry 9}

	psShortTestGroup4 OBJECT-TYPE
	SYNTAX			INTEGER {disconnected(0), connected(1)}
	MAX-ACCESS		read-only
	STATUS			current
	DESCRIPTION		"Connection of group 4 while battery Shorttest."
	::= {psShortTestEntry 10}

	psShortTestGroup5 OBJECT-TYPE
	SYNTAX			INTEGER {disconnected(0), connected(1)}
	MAX-ACCESS		read-only
	STATUS			current
	DESCRIPTION		"Connection of group 5 while battery Short test."
	::= {psShortTestEntry 11}

	psShortTestGroup6 OBJECT-TYPE
	SYNTAX			INTEGER {disconnected(0), connected(1)}
	MAX-ACCESS		read-only
	STATUS			current
	DESCRIPTION		"Connection of group 6 while battery Short test."
	::= {psShortTestEntry 12}

	psShortTestGroup7 OBJECT-TYPE
	SYNTAX			INTEGER {disconnected(0), connected(1)}
	MAX-ACCESS		read-only
	STATUS			current
	DESCRIPTION		"Connection of group 7 while battery Short test."
	::= {psShortTestEntry 13}

	psShortTestGroup8 OBJECT-TYPE
	SYNTAX			INTEGER {disconnected(0), connected(1)}
	MAX-ACCESS		read-only
	STATUS			current
	DESCRIPTION		"Connection of group 8 while battery Short test."
	::= {psShortTestEntry 14}

--END------------------------------------------------------------------------------------------------



	psDischargeTable OBJECT-TYPE
	SYNTAX			SEQUENCE OF PSDischargeEntry
	MAX-ACCESS		not-accessible
	STATUS			current
	DESCRIPTION		"Results of battery discharges."
	::= {psBattery 7}

	psDischargeEntry OBJECT-TYPE
	SYNTAX			PSDischargeEntry
	MAX-ACCESS		not-accessible
	STATUS			current
	DESCRIPTION		""
	INDEX			{psDischargeNumber}
	::= {psDischargeTable 1}

	PSDischargeEntry ::= SEQUENCE
	{
		psDischargeNumber	INTEGER,
		psDischargeStartTime	OCTET STRING,
		psDischargeResult	INTEGER,
		psDischargeLength	INTEGER,
		psDischargeCapacity	INTEGER,
		psDischargeFinalVoltage	INTEGER,
		psDischargeGroup1	INTEGER,
		psDischargeGroup2	INTEGER,
		psDischargeGroup3	INTEGER,
		psDischargeGroup4	INTEGER,
		psDischargeGroup5	INTEGER,
		psDischargeGroup6	INTEGER,
		psDischargeGroup7	INTEGER,
		psDischargeGroup8	INTEGER
	}

	psDischargeNumber OBJECT-TYPE
	SYNTAX			INTEGER (1..4)
	MAX-ACCESS		read-only
	STATUS			current
	DESCRIPTION		"Battery discharge number."
	::= {psDischargeEntry 1}

	psDischargeStartTime OBJECT-TYPE
	SYNTAX			OCTET STRING (SIZE (14))
	MAX-ACCESS		read-only
	STATUS			current
	DESCRIPTION		"Discharge start time(UTC) in format DDMMYYYYhhmmss."
	::= {psDischargeEntry 2}

	psDischargeResult OBJECT-TYPE
	SYNTAX			INTEGER {success(0), unknown(1), user-braked(2), low-current(3), go-charge(4), battery-off(5), timeout(6), mesure-error(7), empty(8), error(9)}
	MAX-ACCESS		read-only
	STATUS			current
	DESCRIPTION		"Battery discharge result."
	::= {psDischargeEntry 3}

	psDischargeLength OBJECT-TYPE
	SYNTAX			INTEGER
	UNITS			"sec"
	MAX-ACCESS		read-only
	STATUS			current
	DESCRIPTION		"Battery discharge duration in seconds."
	::= {psDischargeEntry 4}

	psDischargeCapacity OBJECT-TYPE
	SYNTAX			INTEGER
	UNITS			"0.001A * hour"
	MAX-ACCESS		read-only
	STATUS			current
	DESCRIPTION		"Battery discharge capacity in 0.001A * hour."
	::= {psDischargeEntry 5}

	psDischargeFinalVoltage OBJECT-TYPE
	SYNTAX			INTEGER
	UNITS			"0.01V"
	MAX-ACCESS		read-only
	STATUS			current
	DESCRIPTION		"Output voltage at the end of discharge in 0.01V."
	::= {psDischargeEntry 6}

	psDischargeGroup1 OBJECT-TYPE
	SYNTAX			INTEGER {disconnected(0), connected(1)}
	MAX-ACCESS		read-only
	STATUS			current
	DESCRIPTION		"Connection of group 1 while battery discharge."
	::= {psDischargeEntry 7}

	psDischargeGroup2 OBJECT-TYPE
	SYNTAX			INTEGER {disconnected(0), connected(1)}
	MAX-ACCESS		read-only
	STATUS			current
	DESCRIPTION		"Connection of group 2 while battery discharge."
	::= {psDischargeEntry 8}

	psDischargeGroup3 OBJECT-TYPE
	SYNTAX			INTEGER {disconnected(0), connected(1)}
	MAX-ACCESS		read-only
	STATUS			current
	DESCRIPTION		"Connection of group 3 while battery discharge."
	::= {psDischargeEntry 9}

	psDischargeGroup4 OBJECT-TYPE
	SYNTAX			INTEGER {disconnected(0), connected(1)}
	MAX-ACCESS		read-only
	STATUS			current
	DESCRIPTION		"Connection of group 4 while battery discharge."
	::= {psDischargeEntry 10}

	psDischargeGroup5 OBJECT-TYPE
	SYNTAX			INTEGER {disconnected(0), connected(1)}
	MAX-ACCESS		read-only
	STATUS			current
	DESCRIPTION		"Connection of group 5 while battery discharge."
	::= {psDischargeEntry 11}

	psDischargeGroup6 OBJECT-TYPE
	SYNTAX			INTEGER {disconnected(0), connected(1)}
	MAX-ACCESS		read-only
	STATUS			current
	DESCRIPTION		"Connection of group 6 while battery discharge."
	::= {psDischargeEntry 12}

	psDischargeGroup7 OBJECT-TYPE
	SYNTAX			INTEGER {disconnected(0), connected(1)}
	MAX-ACCESS		read-only
	STATUS			current
	DESCRIPTION		"Connection of group 7 while battery discharge."
	::= {psDischargeEntry 13}

	psDischargeGroup8 OBJECT-TYPE
	SYNTAX			INTEGER {disconnected(0), connected(1)}
	MAX-ACCESS		read-only
	STATUS			current
	DESCRIPTION		"Connection of group 8 while battery discharge."
	::= {psDischargeEntry 14}

	psTestControl OBJECT-TYPE
	SYNTAX			INTEGER {stop(0), run(1)}
	MAX-ACCESS		read-write
	STATUS			current
	DESCRIPTION		"Writing 1 leads to start of battery test. Writing 0 leads to user break of battery test. When test is in progress returns 1, otherwise returns 0."
	::= {psBattery 8}

    psShortTestControl OBJECT-TYPE
	SYNTAX			INTEGER {stop(0), run(1)}
	MAX-ACCESS		read-write
	STATUS			current
	DESCRIPTION		"Writing 1 leads to start of battery Short test. Writing 0 leads to user break of battery Short test. When test is in progress returns 1, otherwise returns 0."
	::= {psBattery 9}

	psEqChargeControl OBJECT-TYPE
	SYNTAX			INTEGER {stop(0), run(1)}
	MAX-ACCESS		read-write
	STATUS			current
	DESCRIPTION		"Writing 1 leads to start of battery equalizing charge. Writing 0 leads to user break of battery equalizing charge. When when equalizing charge is in progress returns 1, otherwise returns 0."
	::= {psBattery 10}

--CONTACTORS

	psContactorTable OBJECT-TYPE
	SYNTAX			SEQUENCE OF PSContactorEntry
	MAX-ACCESS		not-accessible
	STATUS			current
	DESCRIPTION		"Status of contactors."
	::= {psContactors 1}

	psContactorEntry OBJECT-TYPE
	SYNTAX			PSContactorEntry
	MAX-ACCESS		not-accessible
	STATUS			current
	DESCRIPTION		""
	INDEX {psContactorNumber}
	::= {psContactorTable 1}

	PSContactorEntry ::= SEQUENCE
	{
		psContactorNumber	INTEGER,
		psContactorCoil		INTEGER,
		psContactorStatus	INTEGER
	}

	psContactorNumber OBJECT-TYPE
	SYNTAX			INTEGER (1..4)
	MAX-ACCESS		read-only
	STATUS			current
	DESCRIPTION		"contactor number."
	::= {psContactorEntry 1}

	psContactorCoil OBJECT-TYPE
	SYNTAX			INTEGER {off(0), on(1)}
	MAX-ACCESS		read-only
	STATUS			current
	DESCRIPTION		"Contactor coil state."
	::= {psContactorEntry 2}

	psContactorStatus OBJECT-TYPE
	SYNTAX			INTEGER {normal(0), alarm(1), error(2)}
	MAX-ACCESS		read-only
	STATUS			current
	DESCRIPTION		"Contactor status."
	::= {psContactorEntry 3}


	psContactorSycnro OBJECT-TYPE
	SYNTAX			INTEGER {synchronize(1)}
	MAX-ACCESS		read-write
	STATUS			current
	DESCRIPTION		"Writing 1 leads to contactors sincronization procedure. Reading alwayes returns 1."
	::= {psContactors 2}

    psContactorBLVDState OBJECT-TYPE
	SYNTAX			INTEGER {close(1), open(0)}
	MAX-ACCESS		read-write
	STATUS			current
	DESCRIPTION		"Contactor state"
	::= {psContactors 3}

    psContactorL1VDState OBJECT-TYPE
	SYNTAX			INTEGER {close(1), open(0)}
	MAX-ACCESS		read-write
	STATUS			current
	DESCRIPTION		"Contactor state"
	::= {psContactors 4}

    psContactorL2VDState OBJECT-TYPE
	SYNTAX			INTEGER {close(1), open(0)}
	MAX-ACCESS		read-write
	STATUS			current
	DESCRIPTION		"Contactor state"
	::= {psContactors 5}

    psContactorL3VDState OBJECT-TYPE
	SYNTAX			INTEGER {close(1), open(0)}
	MAX-ACCESS		read-write
	STATUS			current
	DESCRIPTION		"Contactor state"
	::= {psContactors 6}

--VBVS

	psVbvTable OBJECT-TYPE
	SYNTAX			SEQUENCE OF PSVbvEntry
	MAX-ACCESS		not-accessible
	STATUS			current
	DESCRIPTION		"status of rectifiers(VBVs)."
	::= {psVbvs 1}

	psVbvEntry OBJECT-TYPE
	SYNTAX			PSVbvEntry
	MAX-ACCESS		not-accessible
	STATUS			current
	DESCRIPTION		""
	INDEX {psVbvNumber}
	::= {psVbvTable 1}

	PSVbvEntry ::= SEQUENCE
	{
		psVbvNumber		 INTEGER,
		psVbvVoltage	 INTEGER,
		psVbvCurrent	 INTEGER,
		psVbvStatus		 INTEGER,
        psVbvInpVoltage  INTEGER,
        psVbvTemperature INTEGER,
        psVbvID          INTEGER
	}

	psVbvNumber OBJECT-TYPE
	SYNTAX			INTEGER (1..60)
	MAX-ACCESS		read-only
	STATUS			current
	DESCRIPTION		"Rectifier(VBV) number."
	::= {psVbvEntry 1}

	psVbvVoltage OBJECT-TYPE
	SYNTAX			INTEGER
	UNITS			"0.01V"
	MAX-ACCESS		read-only
	STATUS			current
	DESCRIPTION		"Rectifier(VBV) output voltage in 0.01V."
	::= {psVbvEntry 2}

	psVbvCurrent OBJECT-TYPE
	SYNTAX			INTEGER
	UNITS			"0.001A"
	MAX-ACCESS		read-only
	STATUS			current
	DESCRIPTION		"Rectifier(VBV) output current in 0.001A."
	::= {psVbvEntry 3}

	psVbvStatus OBJECT-TYPE
	SYNTAX			INTEGER {normal(0), alarm(1), main-salarm(2), overheart(3), overload(4), fan-alarm(5), fan-warning(6), off(7), wrong-type(8), unknown(9), absent(10)}
	MAX-ACCESS		read-only
	STATUS			current
	DESCRIPTION		"Rectifier(VBV) status. If status is unknown(9) or absent(10) the values of psVbvVoltage and psVbvCurrent shold be discarded."
	::= {psVbvEntry 4}

    -------------------------------------------------------------------
    -------------------------------------------------------------------
    psVbvInpVoltage OBJECT-TYPE
    SYNTAX          INTEGER
    UNITS           "1V"
    MAX-ACCESS      read-only
    STATUS          current
    DESCRIPTION     "Rectifier(VBV) input voltage in 1V"
    ::= {psVbvEntry 5}

    psVbvTemperature OBJECT-TYPE
    SYNTAX          INTEGER
    UNITS           "1C"
    MAX-ACCESS      read-only
    STATUS          current
    DESCRIPTION     "Rectifier(VBV) temperature in 1C"
    ::= {psVbvEntry 6}

    psVbvID         OBJECT-TYPE
    SYNTAX          INTEGER
    UNITS           "#"
    MAX-ACCESS      read-only
    STATUS          current
    DESCRIPTION     "Rectifier(VBV) ID Number"
    ::= {psVbvEntry 7}
    -------------------------------------------------------------------
    -------------------------------------------------------------------

--MAINS

	psLineTable OBJECT-TYPE
	SYNTAX			SEQUENCE OF PSLineEntry
	MAX-ACCESS		not-accessible
	STATUS			current
	DESCRIPTION		"Status of mains lines."
	::= {psMains 1}

	psLineEntry OBJECT-TYPE
	SYNTAX			PSLineEntry
	MAX-ACCESS		not-accessible
	STATUS			current
	DESCRIPTION		""
	INDEX {psLineNumber}
	::= {psLineTable 1}

	PSLineEntry ::= SEQUENCE
	{
		psLineNumber		INTEGER,
		psLineVoltage		INTEGER,
		psLineStatus		INTEGER
	}

	psLineNumber OBJECT-TYPE
	SYNTAX			INTEGER (1..3)
	MAX-ACCESS		read-only
	STATUS			current
	DESCRIPTION		"Mains line number."
	::= {psLineEntry 1}

	psLineVoltage OBJECT-TYPE
	SYNTAX			INTEGER
	UNITS			"V"
	MAX-ACCESS		read-only
	STATUS			current
	DESCRIPTION		"Mains line voltage in V."
	::= {psLineEntry 2}

	psLineStatus OBJECT-TYPE
	SYNTAX			INTEGER {value-normal(0), undervoltage(1), overvoltage(2), value-error(3), threshold-normal(4), threshold-alarm(5)}
	MAX-ACCESS		read-only
	STATUS			current
	DESCRIPTION		"Mains line status. If status is value-error(3), threshold-normal(4) or threshold-alarm(5) the value of psLineVoltage should be discarded."
	::= {psLineEntry 3}

	psLightProtStatus OBJECT-TYPE
	SYNTAX			INTEGER {normal(0), alarm(1), error(2), disabled(3)}
	MAX-ACCESS		read-only
	STATUS			current
	DESCRIPTION		"Status of light protection module."
	::= {psMains 2}

-- TEMPERATURE

	psTemperature1 OBJECT-TYPE
	SYNTAX			INTEGER
	UNITS			"0.1degC"
	MAX-ACCESS		read-only
	STATUS			current
	DESCRIPTION		"Temperature of sensor 1 in 0.1degree C."
	::= {psTemperature 1}

	psMeanTemperature1 OBJECT-TYPE
	SYNTAX			INTEGER
	UNITS			"0.1degC"
	MAX-ACCESS		read-only
	STATUS			current
	DESCRIPTION		"Mean temperature of sensor 1 used for temperature compensation of floating voltage."
	::= {psTemperature 2}

	psTemperature1Status OBJECT-TYPE
	SYNTAX			INTEGER {normal(0), error(1)}
	MAX-ACCESS		read-only
	STATUS			current
	DESCRIPTION		"Status of temperature sensor 1. If status is error(1) the values of psTemperature1 and psMeanTemperature1 shold be discarded."
	::= {psTemperature 3}

	psTemperature2 OBJECT-TYPE
	SYNTAX			INTEGER
	UNITS			"0.1degC"
	MAX-ACCESS		read-only
	STATUS			current
	DESCRIPTION		"Temperature of sensor 2 in 0.1degee C."
	::= {psTemperature 4}

	psTemperature2Status OBJECT-TYPE
	SYNTAX			INTEGER {normal(0), under(1), over(2), error(3), disabled(4)}
	MAX-ACCESS		read-only
	STATUS			current
	DESCRIPTION		"Status of temperature sensor 2. If status is error(3) of disabled(4) the value of psTemperature2 shold be discarded."
	::= {psTemperature 5}

--SWITCHES

	psSwitchTable OBJECT-TYPE
	SYNTAX			SEQUENCE OF PSSwitchEntry
	MAX-ACCESS		not-accessible
	STATUS			current
	DESCRIPTION		"Status of switches(discrete inputs)."
	::= {psSwitches 1}

	psSwitchEntry OBJECT-TYPE
	SYNTAX			PSSwitchEntry
	MAX-ACCESS		not-accessible
	STATUS			current
	DESCRIPTION		""
	INDEX {psSwitchNumber}
	::= {psSwitchTable 1}

	PSSwitchEntry ::= SEQUENCE
	{
		psSwitchNumber		INTEGER,
		psSwitchStatus		INTEGER
	}

	psSwitchNumber OBJECT-TYPE
	SYNTAX			INTEGER (1..16)
	MAX-ACCESS		read-only
	STATUS			current
	DESCRIPTION		"Switch(discrete input) number."
	::= {psSwitchEntry 1}

	psSwitchStatus OBJECT-TYPE
	SYNTAX			INTEGER {normal(0), alarm(1), error(2)}
	MAX-ACCESS		read-only
	STATUS			current
	DESCRIPTION		"Switch(discrete input) status."
	::= {psSwitchEntry 2}


--SETTINGS ************************************************************
--Commom
psTimeZone OBJECT-TYPE
	SYNTAX			INTEGER(-48..52)
	MAX-ACCESS		read-write
	STATUS			current
	DESCRIPTION		"Current MAK-4 time zone in 15 min step. 
                                 Exemple 1: Time zone +3h. Set +3h*4 = 12. 
                                 Exemple 2: Time zone +6h. Set +6h*4 = 24"
	::= {psCommonSetting 1}

psBuzzerEnable OBJECT-TYPE
	SYNTAX			INTEGER{disabled(0), enabled(1)}
	MAX-ACCESS		read-write
	STATUS			current
	DESCRIPTION		"Enabled(1) or Disabled (0) buzzer"
	::= {psCommonSetting 2}

--Alarm Masks (begin block) VVVVVVVVVVVVVVVVVVVVVVVVVVVVVVVVVVVVVVVVVVVVVVVVVVVVVVVVVVVVVVVVVVVVVVV
--InternalErrors in psAlarms1Masks
a1InternallError OBJECT-TYPE
    SYNTAX   INTEGER{disabled(0), enabled(1)}
    MAX-ACCESS  read-write
    STATUS   current
    DESCRIPTION "Enabled(1) or Disabled (0)"
    ::= {psAlarms1Masks 1}

--OutputAlarms in psAlarms1Masks
a1LoadUnderVoltageAlarm OBJECT-TYPE
    SYNTAX   INTEGER{disabled(0), enabled(1)}
    MAX-ACCESS  read-write
    STATUS   current
    DESCRIPTION "Enabled(1) or Disabled (0)"
    ::= {psAlarms1Masks 32}

a1LoadOverVoltageAlarm OBJECT-TYPE
    SYNTAX   INTEGER{disabled(0), enabled(1)}
    MAX-ACCESS  read-write
    STATUS   current
    DESCRIPTION "Enabled(1) or Disabled (0)"
    ::= {psAlarms1Masks 33}

a1Termocompensation OBJECT-TYPE
    SYNTAX   INTEGER{disabled(0), enabled(1)}
    MAX-ACCESS  read-write
    STATUS   current
    DESCRIPTION "Enabled(1) or Disabled (0)"
    ::= {psAlarms1Masks 34}

--LoadFuses in psAlarms1Masks
a1LoadFuses1 OBJECT-TYPE
    SYNTAX   INTEGER{disabled(0), enabled(1)}
    MAX-ACCESS  read-write
    STATUS   current
    DESCRIPTION "Enabled(1) or Disabled (0)"
    ::= {psAlarms1Masks 35}

a1LoadFuses2 OBJECT-TYPE
    SYNTAX   INTEGER{disabled(0), enabled(1)}
    MAX-ACCESS  read-write
    STATUS   current
    DESCRIPTION "Enabled(1) or Disabled (0)"
    ::= {psAlarms1Masks 36}

a1LoadFuses3 OBJECT-TYPE
    SYNTAX   INTEGER{disabled(0), enabled(1)}
    MAX-ACCESS  read-write
    STATUS   current
    DESCRIPTION "Enabled(1) or Disabled (0)"
    ::= {psAlarms1Masks 37}

a1LoadFuses4 OBJECT-TYPE
    SYNTAX   INTEGER{disabled(0), enabled(1)}
    MAX-ACCESS  read-write
    STATUS   current
    DESCRIPTION "Enabled(1) or Disabled (0)"
    ::= {psAlarms1Masks 38}

a1LoadFuses5 OBJECT-TYPE
    SYNTAX   INTEGER{disabled(0), enabled(1)}
    MAX-ACCESS  read-write
    STATUS   current
    DESCRIPTION "Enabled(1) or Disabled (0)"
    ::= {psAlarms1Masks 39}

a1LoadFuses6 OBJECT-TYPE
    SYNTAX   INTEGER{disabled(0), enabled(1)}
    MAX-ACCESS  read-write
    STATUS   current
    DESCRIPTION "Enabled(1) or Disabled (0)"
    ::= {psAlarms1Masks 40}

a1LoadFuses7 OBJECT-TYPE
    SYNTAX   INTEGER{disabled(0), enabled(1)}
    MAX-ACCESS  read-write
    STATUS   current
    DESCRIPTION "Enabled(1) or Disabled (0)"
    ::= {psAlarms1Masks 41}

a1LoadFuses8 OBJECT-TYPE
    SYNTAX   INTEGER{disabled(0), enabled(1)}
    MAX-ACCESS  read-write
    STATUS   current
    DESCRIPTION "Enabled(1) or Disabled (0)"
    ::= {psAlarms1Masks 42}

a1LoadFuses9 OBJECT-TYPE
    SYNTAX   INTEGER{disabled(0), enabled(1)}
    MAX-ACCESS  read-write
    STATUS   current
    DESCRIPTION "Enabled(1) or Disabled (0)"
    ::= {psAlarms1Masks 43}

a1LoadFuses10 OBJECT-TYPE
    SYNTAX   INTEGER{disabled(0), enabled(1)}
    MAX-ACCESS  read-write
    STATUS   current
    DESCRIPTION "Enabled(1) or Disabled (0)"
    ::= {psAlarms1Masks 44}

a1LoadFuses11 OBJECT-TYPE
    SYNTAX   INTEGER{disabled(0), enabled(1)}
    MAX-ACCESS  read-write
    STATUS   current
    DESCRIPTION "Enabled(1) or Disabled (0)"
    ::= {psAlarms1Masks 45}

a1LoadFuses12 OBJECT-TYPE
    SYNTAX   INTEGER{disabled(0), enabled(1)}
    MAX-ACCESS  read-write
    STATUS   current
    DESCRIPTION "Enabled(1) or Disabled (0)"
    ::= {psAlarms1Masks 46}

a1LoadFuses13 OBJECT-TYPE
    SYNTAX   INTEGER{disabled(0), enabled(1)}
    MAX-ACCESS  read-write
    STATUS   current
    DESCRIPTION "Enabled(1) or Disabled (0)"
    ::= {psAlarms1Masks 47}

a1LoadFuses14 OBJECT-TYPE
    SYNTAX   INTEGER{disabled(0), enabled(1)}
    MAX-ACCESS  read-write
    STATUS   current
    DESCRIPTION "Enabled(1) or Disabled (0)"
    ::= {psAlarms1Masks 48}

a1LoadFuses15 OBJECT-TYPE
    SYNTAX   INTEGER{disabled(0), enabled(1)}
    MAX-ACCESS  read-write
    STATUS   current
    DESCRIPTION "Enabled(1) or Disabled (0)"
    ::= {psAlarms1Masks 49}

a1LoadFuses16 OBJECT-TYPE
    SYNTAX   INTEGER{disabled(0), enabled(1)}
    MAX-ACCESS  read-write
    STATUS   current
    DESCRIPTION "Enabled(1) or Disabled (0)"
    ::= {psAlarms1Masks 50}

a1LoadFuses17 OBJECT-TYPE
    SYNTAX   INTEGER{disabled(0), enabled(1)}
    MAX-ACCESS  read-write
    STATUS   current
    DESCRIPTION "Enabled(1) or Disabled (0)"
    ::= {psAlarms1Masks 51}

a1LoadFuses18 OBJECT-TYPE
    SYNTAX   INTEGER{disabled(0), enabled(1)}
    MAX-ACCESS  read-write
    STATUS   current
    DESCRIPTION "Enabled(1) or Disabled (0)"
    ::= {psAlarms1Masks 52}

a1LoadFuses19 OBJECT-TYPE
    SYNTAX   INTEGER{disabled(0), enabled(1)}
    MAX-ACCESS  read-write
    STATUS   current
    DESCRIPTION "Enabled(1) or Disabled (0)"
    ::= {psAlarms1Masks 53}

a1LoadFuses20 OBJECT-TYPE
    SYNTAX   INTEGER{disabled(0), enabled(1)}
    MAX-ACCESS  read-write
    STATUS   current
    DESCRIPTION "Enabled(1) or Disabled (0)"
    ::= {psAlarms1Masks 54}

a1LoadFuses21 OBJECT-TYPE
    SYNTAX   INTEGER{disabled(0), enabled(1)}
    MAX-ACCESS  read-write
    STATUS   current
    DESCRIPTION "Enabled(1) or Disabled (0)"
    ::= {psAlarms1Masks 55}

a1LoadFuses22 OBJECT-TYPE
    SYNTAX   INTEGER{disabled(0), enabled(1)}
    MAX-ACCESS  read-write
    STATUS   current
    DESCRIPTION "Enabled(1) or Disabled (0)"
    ::= {psAlarms1Masks 56}

a1LoadFuses23 OBJECT-TYPE
    SYNTAX   INTEGER{disabled(0), enabled(1)}
    MAX-ACCESS  read-write
    STATUS   current
    DESCRIPTION "Enabled(1) or Disabled (0)"
    ::= {psAlarms1Masks 57}

a1LoadFuses24 OBJECT-TYPE
    SYNTAX   INTEGER{disabled(0), enabled(1)}
    MAX-ACCESS  read-write
    STATUS   current
    DESCRIPTION "Enabled(1) or Disabled (0)"
    ::= {psAlarms1Masks 58}

a1LoadFuses25 OBJECT-TYPE
    SYNTAX   INTEGER{disabled(0), enabled(1)}
    MAX-ACCESS  read-write
    STATUS   current
    DESCRIPTION "Enabled(1) or Disabled (0)"
    ::= {psAlarms1Masks 59}

a1LoadFuses26 OBJECT-TYPE
    SYNTAX   INTEGER{disabled(0), enabled(1)}
    MAX-ACCESS  read-write
    STATUS   current
    DESCRIPTION "Enabled(1) or Disabled (0)"
    ::= {psAlarms1Masks 60}

a1LoadFuses27 OBJECT-TYPE
    SYNTAX   INTEGER{disabled(0), enabled(1)}
    MAX-ACCESS  read-write
    STATUS   current
    DESCRIPTION "Enabled(1) or Disabled (0)"
    ::= {psAlarms1Masks 61}

a1LoadFuses28 OBJECT-TYPE
    SYNTAX   INTEGER{disabled(0), enabled(1)}
    MAX-ACCESS  read-write
    STATUS   current
    DESCRIPTION "Enabled(1) or Disabled (0)"
    ::= {psAlarms1Masks 62}

a1LoadFuses29 OBJECT-TYPE
    SYNTAX   INTEGER{disabled(0), enabled(1)}
    MAX-ACCESS  read-write
    STATUS   current
    DESCRIPTION "Enabled(1) or Disabled (0)"
    ::= {psAlarms1Masks 63}

a1LoadFuses30 OBJECT-TYPE
    SYNTAX   INTEGER{disabled(0), enabled(1)}
    MAX-ACCESS  read-write
    STATUS   current
    DESCRIPTION "Enabled(1) or Disabled (0)"
    ::= {psAlarms1Masks 64}

a1LoadFuses31 OBJECT-TYPE
    SYNTAX   INTEGER{disabled(0), enabled(1)}
    MAX-ACCESS  read-write
    STATUS   current
    DESCRIPTION "Enabled(1) or Disabled (0)"
    ::= {psAlarms1Masks 65}

a1LoadFuses32 OBJECT-TYPE
    SYNTAX   INTEGER{disabled(0), enabled(1)}
    MAX-ACCESS  read-write
    STATUS   current
    DESCRIPTION "Enabled(1) or Disabled (0)"
    ::= {psAlarms1Masks 66}

a1LoadFuses33 OBJECT-TYPE
    SYNTAX   INTEGER{disabled(0), enabled(1)}
    MAX-ACCESS  read-write
    STATUS   current
    DESCRIPTION "Enabled(1) or Disabled (0)"
    ::= {psAlarms1Masks 67}

a1LoadFuses34 OBJECT-TYPE
    SYNTAX   INTEGER{disabled(0), enabled(1)}
    MAX-ACCESS  read-write
    STATUS   current
    DESCRIPTION "Enabled(1) or Disabled (0)"
    ::= {psAlarms1Masks 68}

a1LoadFuses35 OBJECT-TYPE
    SYNTAX   INTEGER{disabled(0), enabled(1)}
    MAX-ACCESS  read-write
    STATUS   current
    DESCRIPTION "Enabled(1) or Disabled (0)"
    ::= {psAlarms1Masks 69}

a1LoadFuses36 OBJECT-TYPE
    SYNTAX   INTEGER{disabled(0), enabled(1)}
    MAX-ACCESS  read-write
    STATUS   current
    DESCRIPTION "Enabled(1) or Disabled (0)"
    ::= {psAlarms1Masks 70}

a1LoadFuses37 OBJECT-TYPE
    SYNTAX   INTEGER{disabled(0), enabled(1)}
    MAX-ACCESS  read-write
    STATUS   current
    DESCRIPTION "Enabled(1) or Disabled (0)"
    ::= {psAlarms1Masks 71}

a1LoadFuses38 OBJECT-TYPE
    SYNTAX   INTEGER{disabled(0), enabled(1)}
    MAX-ACCESS  read-write
    STATUS   current
    DESCRIPTION "Enabled(1) or Disabled (0)"
    ::= {psAlarms1Masks 72}

a1LoadFuses39 OBJECT-TYPE
    SYNTAX   INTEGER{disabled(0), enabled(1)}
    MAX-ACCESS  read-write
    STATUS   current
    DESCRIPTION "Enabled(1) or Disabled (0)"
    ::= {psAlarms1Masks 73}

a1LoadFuses40 OBJECT-TYPE
    SYNTAX   INTEGER{disabled(0), enabled(1)}
    MAX-ACCESS  read-write
    STATUS   current
    DESCRIPTION "Enabled(1) or Disabled (0)"
    ::= {psAlarms1Masks 74}

a1LoadFuses41 OBJECT-TYPE
    SYNTAX   INTEGER{disabled(0), enabled(1)}
    MAX-ACCESS  read-write
    STATUS   current
    DESCRIPTION "Enabled(1) or Disabled (0)"
    ::= {psAlarms1Masks 75}

a1LoadFuses42 OBJECT-TYPE
    SYNTAX   INTEGER{disabled(0), enabled(1)}
    MAX-ACCESS  read-write
    STATUS   current
    DESCRIPTION "Enabled(1) or Disabled (0)"
    ::= {psAlarms1Masks 76}

a1LoadFuses43 OBJECT-TYPE
    SYNTAX   INTEGER{disabled(0), enabled(1)}
    MAX-ACCESS  read-write
    STATUS   current
    DESCRIPTION "Enabled(1) or Disabled (0)"
    ::= {psAlarms1Masks 77}

a1LoadFuses44 OBJECT-TYPE
    SYNTAX   INTEGER{disabled(0), enabled(1)}
    MAX-ACCESS  read-write
    STATUS   current
    DESCRIPTION "Enabled(1) or Disabled (0)"
    ::= {psAlarms1Masks 78}

a1LoadFuses45 OBJECT-TYPE
    SYNTAX   INTEGER{disabled(0), enabled(1)}
    MAX-ACCESS  read-write
    STATUS   current
    DESCRIPTION "Enabled(1) or Disabled (0)"
    ::= {psAlarms1Masks 79}

a1LoadFuses46 OBJECT-TYPE
    SYNTAX   INTEGER{disabled(0), enabled(1)}
    MAX-ACCESS  read-write
    STATUS   current
    DESCRIPTION "Enabled(1) or Disabled (0)"
    ::= {psAlarms1Masks 80}

a1LoadFuses47 OBJECT-TYPE
    SYNTAX   INTEGER{disabled(0), enabled(1)}
    MAX-ACCESS  read-write
    STATUS   current
    DESCRIPTION "Enabled(1) or Disabled (0)"
    ::= {psAlarms1Masks 81}

a1LoadFuses48 OBJECT-TYPE
    SYNTAX   INTEGER{disabled(0), enabled(1)}
    MAX-ACCESS  read-write
    STATUS   current
    DESCRIPTION "Enabled(1) or Disabled (0)"
    ::= {psAlarms1Masks 82}

a1LoadFuses49 OBJECT-TYPE
    SYNTAX   INTEGER{disabled(0), enabled(1)}
    MAX-ACCESS  read-write
    STATUS   current
    DESCRIPTION "Enabled(1) or Disabled (0)"
    ::= {psAlarms1Masks 83}

a1LoadFuses50 OBJECT-TYPE
    SYNTAX   INTEGER{disabled(0), enabled(1)}
    MAX-ACCESS  read-write
    STATUS   current
    DESCRIPTION "Enabled(1) or Disabled (0)"
    ::= {psAlarms1Masks 84}

a1LoadFuses51 OBJECT-TYPE
    SYNTAX   INTEGER{disabled(0), enabled(1)}
    MAX-ACCESS  read-write
    STATUS   current
    DESCRIPTION "Enabled(1) or Disabled (0)"
    ::= {psAlarms1Masks 85}

a1LoadFuses52 OBJECT-TYPE
    SYNTAX   INTEGER{disabled(0), enabled(1)}
    MAX-ACCESS  read-write
    STATUS   current
    DESCRIPTION "Enabled(1) or Disabled (0)"
    ::= {psAlarms1Masks 86}

a1UKDVAlarm OBJECT-TYPE
    SYNTAX   INTEGER{disabled(0), enabled(1)}
    MAX-ACCESS  read-write
    STATUS   current
    DESCRIPTION "Enabled(1) or Disabled (0)"
    ::= {psAlarms1Masks 87}

--Battery Events in psAlarms1Masks
a1BatteryDischarge OBJECT-TYPE
    SYNTAX   INTEGER{disabled(0), enabled(1)}
    MAX-ACCESS  read-write
    STATUS   current
    DESCRIPTION "Enabled(1) or Disabled (0)"
    ::= {psAlarms1Masks 96}

a1LowBatteryVoltage OBJECT-TYPE
    SYNTAX   INTEGER{disabled(0), enabled(1)}
    MAX-ACCESS  read-write
    STATUS   current
    DESCRIPTION "Enabled(1) or Disabled (0)"
    ::= {psAlarms1Masks 97}

a1BatteryCharge OBJECT-TYPE
    SYNTAX   INTEGER{disabled(0), enabled(1)}
    MAX-ACCESS  read-write
    STATUS   current
    DESCRIPTION "Enabled(1) or Disabled (0)"
    ::= {psAlarms1Masks 98}

a1BatteryBoost OBJECT-TYPE
    SYNTAX   INTEGER{disabled(0), enabled(1)}
    MAX-ACCESS  read-write
    STATUS   current
    DESCRIPTION "Enabled(1) or Disabled (0)"
    ::= {psAlarms1Masks 99}

a1BatteryFloat OBJECT-TYPE
    SYNTAX   INTEGER{disabled(0), enabled(1)}
    MAX-ACCESS  read-write
    STATUS   current
    DESCRIPTION "Enabled(1) or Disabled (0)"
    ::= {psAlarms1Masks 100}

a1BatteryEqualize OBJECT-TYPE
    SYNTAX   INTEGER{disabled(0), enabled(1)}
    MAX-ACCESS  read-write
    STATUS   current
    DESCRIPTION "Enabled(1) or Disabled (0)"
    ::= {psAlarms1Masks 101}

a1BatteryTest OBJECT-TYPE
    SYNTAX   INTEGER{disabled(0), enabled(1)}
    MAX-ACCESS  read-write
    STATUS   current
    DESCRIPTION "Enabled(1) or Disabled (0)"
    ::= {psAlarms1Masks 102}

a1BatteryFuse1Off OBJECT-TYPE
    SYNTAX   INTEGER{disabled(0), enabled(1)}
    MAX-ACCESS  read-write
    STATUS   current
    DESCRIPTION "Enabled(1) or Disabled (0)"
    ::= {psAlarms1Masks 103}

a1BatteryFuse2Off OBJECT-TYPE
    SYNTAX   INTEGER{disabled(0), enabled(1)}
    MAX-ACCESS  read-write
    STATUS   current
    DESCRIPTION "Enabled(1) or Disabled (0)"
    ::= {psAlarms1Masks 104}

a1BatteryFuse3Off OBJECT-TYPE
    SYNTAX   INTEGER{disabled(0), enabled(1)}
    MAX-ACCESS  read-write
    STATUS   current
    DESCRIPTION "Enabled(1) or Disabled (0)"
    ::= {psAlarms1Masks 105}

a1BatteryFuse4Off OBJECT-TYPE
    SYNTAX   INTEGER{disabled(0), enabled(1)}
    MAX-ACCESS  read-write
    STATUS   current
    DESCRIPTION "Enabled(1) or Disabled (0)"
    ::= {psAlarms1Masks 106}

---------------------------------------------------

a1BatteryBlockElGr1Alarm OBJECT-TYPE
    SYNTAX   INTEGER{disabled(0), enabled(1)}
    MAX-ACCESS  read-write
    STATUS   current
    DESCRIPTION "Enabled(1) or Disabled (0)"
    ::= {psAlarms1Masks 111}

a1BatteryBlockElGr2Alarm OBJECT-TYPE
    SYNTAX   INTEGER{disabled(0), enabled(1)}
    MAX-ACCESS  read-write
    STATUS   current
    DESCRIPTION "Enabled(1) or Disabled (0)"
    ::= {psAlarms1Masks 112}

a1BatteryBlockElGr3Alarm OBJECT-TYPE
    SYNTAX   INTEGER{disabled(0), enabled(1)}
    MAX-ACCESS  read-write
    STATUS   current
    DESCRIPTION "Enabled(1) or Disabled (0)"
    ::= {psAlarms1Masks 113}

a1BatteryBlockElGr4Alarm OBJECT-TYPE
    SYNTAX   INTEGER{disabled(0), enabled(1)}
    MAX-ACCESS  read-write
    STATUS   current
    DESCRIPTION "Enabled(1) or Disabled (0)"
    ::= {psAlarms1Masks 114}
----------------------------------------------------

a1UPKBAlarm OBJECT-TYPE
    SYNTAX   INTEGER{disabled(0), enabled(1)}
    MAX-ACCESS  read-write
    STATUS   current
    DESCRIPTION "Enabled(1) or Disabled (0)"
    ::= {psAlarms1Masks 119}

a1ChargeCurrentLess1A OBJECT-TYPE
    SYNTAX   INTEGER{disabled(0), enabled(1)}
    MAX-ACCESS  read-write
    STATUS   current
    DESCRIPTION "Enabled(1) or Disabled (0)"
    ::= {psAlarms1Masks 120}

a1ChargeCurrentLess2A OBJECT-TYPE
    SYNTAX   INTEGER{disabled(0), enabled(1)}
    MAX-ACCESS  read-write
    STATUS   current
    DESCRIPTION "Enabled(1) or Disabled (0)"
    ::= {psAlarms1Masks 121}

a1ChargeCurrentLess3A OBJECT-TYPE
    SYNTAX   INTEGER{disabled(0), enabled(1)}
    MAX-ACCESS  read-write
    STATUS   current
    DESCRIPTION "Enabled(1) or Disabled (0)"
    ::= {psAlarms1Masks 122}

a1ChargeCurrentLess4A OBJECT-TYPE
    SYNTAX   INTEGER{disabled(0), enabled(1)}
    MAX-ACCESS  read-write
    STATUS   current
    DESCRIPTION "Enabled(1) or Disabled (0)"
    ::= {psAlarms1Masks 123}

a1ChargeCurrentLess5A OBJECT-TYPE
    SYNTAX   INTEGER{disabled(0), enabled(1)}
    MAX-ACCESS  read-write
    STATUS   current
    DESCRIPTION "Enabled(1) or Disabled (0)"
    ::= {psAlarms1Masks 124}

a1BatteryOverheat OBJECT-TYPE
    SYNTAX   INTEGER{disabled(0), enabled(1)}
    MAX-ACCESS  read-write
    STATUS   current
    DESCRIPTION "Enabled(1) or Disabled (0)"
    ::= {psAlarms1Masks 125}

-------------------------------------------------------------------------------------------
-------------------------------------------------------------------------------------------
a1BatteryShortTest OBJECT-TYPE
    SYNTAX   INTEGER{disabled(0), enabled(1)}
    MAX-ACCESS  read-write
    STATUS   current
    DESCRIPTION "Enabled(1) or Disabled (0)"
    ::= {psAlarms1Masks 126}

a1BatteryShortTestFail OBJECT-TYPE  
    SYNTAX   INTEGER{disabled(0), enabled(1)}
    MAX-ACCESS  read-write
    STATUS   current
    DESCRIPTION "Enabled(1) or Disabled (0)"
    ::= {psAlarms1Masks 127}

-------------------------------------------------------------------------------------------
-------------------------------------------------------------------------------------------

a1BLVDoff OBJECT-TYPE
    SYNTAX   INTEGER{disabled(0), enabled(1)}
    MAX-ACCESS  read-write
    STATUS   current
    DESCRIPTION "Enabled(1) or Disabled (0)"
    ::= {psAlarms1Masks 128}

a1LLVD1off OBJECT-TYPE
    SYNTAX   INTEGER{disabled(0), enabled(1)}
    MAX-ACCESS  read-write
    STATUS   current
    DESCRIPTION "Enabled(1) or Disabled (0)"
    ::= {psAlarms1Masks 129}

a1LLVD2off OBJECT-TYPE
    SYNTAX   INTEGER{disabled(0), enabled(1)}
    MAX-ACCESS  read-write
    STATUS   current
    DESCRIPTION "Enabled(1) or Disabled (0)"
    ::= {psAlarms1Masks 130}

--VBVAlarm in psAlarms1Masks
a1VBV1Alarm OBJECT-TYPE
    SYNTAX   INTEGER{disabled(0), enabled(1)}
    MAX-ACCESS  read-write
    STATUS   current
    DESCRIPTION "Alarm of rectifier1 Enabled(1) or Disabled (0)"
    ::= {psAlarms1Masks 160}

a1VBV2Alarm OBJECT-TYPE
    SYNTAX   INTEGER{disabled(0), enabled(1)}
    MAX-ACCESS  read-write
    STATUS   current
    DESCRIPTION "Alarm of rectifier2 Enabled(1) or Disabled (0)"
    ::= {psAlarms1Masks 161}

a1VBV3Alarm OBJECT-TYPE
    SYNTAX   INTEGER{disabled(0), enabled(1)}
    MAX-ACCESS  read-write
    STATUS   current
    DESCRIPTION "Alarm of rectifier3 Enabled(1) or Disabled (0)"
    ::= {psAlarms1Masks 162}

a1VBV4Alarm OBJECT-TYPE
    SYNTAX   INTEGER{disabled(0), enabled(1)}
    MAX-ACCESS  read-write
    STATUS   current
    DESCRIPTION "Alarm of rectifier4 Enabled(1) or Disabled (0)"
    ::= {psAlarms1Masks 163}

a1VBV5Alarm OBJECT-TYPE
    SYNTAX   INTEGER{disabled(0), enabled(1)}
    MAX-ACCESS  read-write
    STATUS   current
    DESCRIPTION "Alarm of rectifier5 Enabled(1) or Disabled (0)"
    ::= {psAlarms1Masks 164}

a1VBV6Alarm OBJECT-TYPE
    SYNTAX   INTEGER{disabled(0), enabled(1)}
    MAX-ACCESS  read-write
    STATUS   current
    DESCRIPTION "Alarm of rectifier6 Enabled(1) or Disabled (0)"
    ::= {psAlarms1Masks 165}

a1VBV7Alarm OBJECT-TYPE
    SYNTAX   INTEGER{disabled(0), enabled(1)}
    MAX-ACCESS  read-write
    STATUS   current
    DESCRIPTION "Alarm of rectifier7 Enabled(1) or Disabled (0)"
    ::= {psAlarms1Masks 166}

a1VBV8Alarm OBJECT-TYPE
    SYNTAX   INTEGER{disabled(0), enabled(1)}
    MAX-ACCESS  read-write
    STATUS   current
    DESCRIPTION "Alarm of rectifier8 Enabled(1) or Disabled (0)"
    ::= {psAlarms1Masks 167}

a1VBV9Alarm OBJECT-TYPE
    SYNTAX   INTEGER{disabled(0), enabled(1)}
    MAX-ACCESS  read-write
    STATUS   current
    DESCRIPTION "Alarm of rectifier9 Enabled(1) or Disabled (0)"
    ::= {psAlarms1Masks 168}

a1VBV10Alarm OBJECT-TYPE
    SYNTAX   INTEGER{disabled(0), enabled(1)}
    MAX-ACCESS  read-write
    STATUS   current
    DESCRIPTION "Alarm of rectifier10 Enabled(1) or Disabled (0)"
    ::= {psAlarms1Masks 169}

a1VBV11Alarm OBJECT-TYPE
    SYNTAX   INTEGER{disabled(0), enabled(1)}
    MAX-ACCESS  read-write
    STATUS   current
    DESCRIPTION "Alarm of rectifier11 Enabled(1) or Disabled (0)"
    ::= {psAlarms1Masks 170}

a1VBV12Alarm OBJECT-TYPE
    SYNTAX   INTEGER{disabled(0), enabled(1)}
    MAX-ACCESS  read-write
    STATUS   current
    DESCRIPTION "Alarm of rectifier12 Enabled(1) or Disabled (0)"
    ::= {psAlarms1Masks 171}

a1VBV13Alarm OBJECT-TYPE
    SYNTAX   INTEGER{disabled(0), enabled(1)}
    MAX-ACCESS  read-write
    STATUS   current
    DESCRIPTION "Alarm of rectifier13 Enabled(1) or Disabled (0)"
    ::= {psAlarms1Masks 172}

a1VBV14Alarm OBJECT-TYPE
    SYNTAX   INTEGER{disabled(0), enabled(1)}
    MAX-ACCESS  read-write
    STATUS   current
    DESCRIPTION "Alarm of rectifier14 Enabled(1) or Disabled (0)"
    ::= {psAlarms1Masks 173}

a1VBV15Alarm OBJECT-TYPE
    SYNTAX   INTEGER{disabled(0), enabled(1)}
    MAX-ACCESS  read-write
    STATUS   current
    DESCRIPTION "Alarm of rectifier15 Enabled(1) or Disabled (0)"
    ::= {psAlarms1Masks 174}

a1VBV16Alarm OBJECT-TYPE
    SYNTAX   INTEGER{disabled(0), enabled(1)}
    MAX-ACCESS  read-write
    STATUS   current
    DESCRIPTION "Alarm of rectifier16 Enabled(1) or Disabled (0)"
    ::= {psAlarms1Masks 175}

a1VBV17Alarm OBJECT-TYPE
    SYNTAX   INTEGER{disabled(0), enabled(1)}
    MAX-ACCESS  read-write
    STATUS   current
    DESCRIPTION "Alarm of rectifier17 Enabled(1) or Disabled (0)"
    ::= {psAlarms1Masks 176}

a1VBV18Alarm OBJECT-TYPE
    SYNTAX   INTEGER{disabled(0), enabled(1)}
    MAX-ACCESS  read-write
    STATUS   current
    DESCRIPTION "Alarm of rectifier18 Enabled(1) or Disabled (0)"
    ::= {psAlarms1Masks 177}

a1VBV19Alarm OBJECT-TYPE
    SYNTAX   INTEGER{disabled(0), enabled(1)}
    MAX-ACCESS  read-write
    STATUS   current
    DESCRIPTION "Alarm of rectifier19 Enabled(1) or Disabled (0)"
    ::= {psAlarms1Masks 178}

a1VBV20Alarm OBJECT-TYPE
    SYNTAX   INTEGER{disabled(0), enabled(1)}
    MAX-ACCESS  read-write
    STATUS   current
    DESCRIPTION "Alarm of rectifier20 Enabled(1) or Disabled (0)"
    ::= {psAlarms1Masks 179}

a1VBV21Alarm OBJECT-TYPE
    SYNTAX   INTEGER{disabled(0), enabled(1)}
    MAX-ACCESS  read-write
    STATUS   current
    DESCRIPTION "Alarm of rectifier21 Enabled(1) or Disabled (0)"
    ::= {psAlarms1Masks 180}

a1VBV22Alarm OBJECT-TYPE
    SYNTAX   INTEGER{disabled(0), enabled(1)}
    MAX-ACCESS  read-write
    STATUS   current
    DESCRIPTION "Alarm of rectifier22 Enabled(1) or Disabled (0)"
    ::= {psAlarms1Masks 181}

a1VBV23Alarm OBJECT-TYPE
    SYNTAX   INTEGER{disabled(0), enabled(1)}
    MAX-ACCESS  read-write
    STATUS   current
    DESCRIPTION "Alarm of rectifier23 Enabled(1) or Disabled (0)"
    ::= {psAlarms1Masks 182}

a1VBV24Alarm OBJECT-TYPE
    SYNTAX   INTEGER{disabled(0), enabled(1)}
    MAX-ACCESS  read-write
    STATUS   current
    DESCRIPTION "Alarm of rectifier24 Enabled(1) or Disabled (0)"
    ::= {psAlarms1Masks 183}

a1VBV25Alarm OBJECT-TYPE
    SYNTAX   INTEGER{disabled(0), enabled(1)}
    MAX-ACCESS  read-write
    STATUS   current
    DESCRIPTION "Alarm of rectifier25 Enabled(1) or Disabled (0)"
    ::= {psAlarms1Masks 184}

a1VBV26Alarm OBJECT-TYPE
    SYNTAX   INTEGER{disabled(0), enabled(1)}
    MAX-ACCESS  read-write
    STATUS   current
    DESCRIPTION "Alarm of rectifier26 Enabled(1) or Disabled (0)"
    ::= {psAlarms1Masks 185}

a1VBV27Alarm OBJECT-TYPE
    SYNTAX   INTEGER{disabled(0), enabled(1)}
    MAX-ACCESS  read-write
    STATUS   current
    DESCRIPTION "Alarm of rectifier27 Enabled(1) or Disabled (0)"
    ::= {psAlarms1Masks 186}

a1VBV28Alarm OBJECT-TYPE
    SYNTAX   INTEGER{disabled(0), enabled(1)}
    MAX-ACCESS  read-write
    STATUS   current
    DESCRIPTION "Alarm of rectifier28 Enabled(1) or Disabled (0)"
    ::= {psAlarms1Masks 187}

a1VBV29Alarm OBJECT-TYPE
    SYNTAX   INTEGER{disabled(0), enabled(1)}
    MAX-ACCESS  read-write
    STATUS   current
    DESCRIPTION "Alarm of rectifier29 Enabled(1) or Disabled (0)"
    ::= {psAlarms1Masks 188}

a1VBV30Alarm OBJECT-TYPE
    SYNTAX   INTEGER{disabled(0), enabled(1)}
    MAX-ACCESS  read-write
    STATUS   current
    DESCRIPTION "Alarm of rectifier30 Enabled(1) or Disabled (0)"
    ::= {psAlarms1Masks 189}

a1VBV31Alarm OBJECT-TYPE
    SYNTAX   INTEGER{disabled(0), enabled(1)}
    MAX-ACCESS  read-write
    STATUS   current
    DESCRIPTION "Alarm of rectifier31 Enabled(1) or Disabled (0)"
    ::= {psAlarms1Masks 190}

a1VBV32Alarm OBJECT-TYPE
    SYNTAX   INTEGER{disabled(0), enabled(1)}
    MAX-ACCESS  read-write
    STATUS   current
    DESCRIPTION "Alarm of rectifier32 Enabled(1) or Disabled (0)"
    ::= {psAlarms1Masks 191}

a1VBV33Alarm OBJECT-TYPE
    SYNTAX   INTEGER{disabled(0), enabled(1)}
    MAX-ACCESS  read-write
    STATUS   current
    DESCRIPTION "Alarm of rectifier33 Enabled(1) or Disabled (0)"
    ::= {psAlarms1Masks 192}

a1VBV34Alarm OBJECT-TYPE
    SYNTAX   INTEGER{disabled(0), enabled(1)}
    MAX-ACCESS  read-write
    STATUS   current
    DESCRIPTION "Alarm of rectifier34 Enabled(1) or Disabled (0)"
    ::= {psAlarms1Masks 193}

a1VBV35Alarm OBJECT-TYPE
    SYNTAX   INTEGER{disabled(0), enabled(1)}
    MAX-ACCESS  read-write
    STATUS   current
    DESCRIPTION "Alarm of rectifier35 Enabled(1) or Disabled (0)"
    ::= {psAlarms1Masks 194}

a1VBV36Alarm OBJECT-TYPE
    SYNTAX   INTEGER{disabled(0), enabled(1)}
    MAX-ACCESS  read-write
    STATUS   current
    DESCRIPTION "Alarm of rectifier36 Enabled(1) or Disabled (0)"
    ::= {psAlarms1Masks 195}

a1VBV37Alarm OBJECT-TYPE
    SYNTAX   INTEGER{disabled(0), enabled(1)}
    MAX-ACCESS  read-write
    STATUS   current
    DESCRIPTION "Alarm of rectifier37 Enabled(1) or Disabled (0)"
    ::= {psAlarms1Masks 196}

a1VBV38Alarm OBJECT-TYPE
    SYNTAX   INTEGER{disabled(0), enabled(1)}
    MAX-ACCESS  read-write
    STATUS   current
    DESCRIPTION "Alarm of rectifier38 Enabled(1) or Disabled (0)"
    ::= {psAlarms1Masks 197}

a1VBV39Alarm OBJECT-TYPE
    SYNTAX   INTEGER{disabled(0), enabled(1)}
    MAX-ACCESS  read-write
    STATUS   current
    DESCRIPTION "Alarm of rectifier39 Enabled(1) or Disabled (0)"
    ::= {psAlarms1Masks 198}

a1VBV40Alarm OBJECT-TYPE
    SYNTAX   INTEGER{disabled(0), enabled(1)}
    MAX-ACCESS  read-write
    STATUS   current
    DESCRIPTION "Alarm of rectifier40 Enabled(1) or Disabled (0)"
    ::= {psAlarms1Masks 199}

a1VBV41Alarm OBJECT-TYPE
    SYNTAX   INTEGER{disabled(0), enabled(1)}
    MAX-ACCESS  read-write
    STATUS   current
    DESCRIPTION "Alarm of rectifier41 Enabled(1) or Disabled (0)"
    ::= {psAlarms1Masks 200}

a1VBV42Alarm OBJECT-TYPE
    SYNTAX   INTEGER{disabled(0), enabled(1)}
    MAX-ACCESS  read-write
    STATUS   current
    DESCRIPTION "Alarm of rectifier42 Enabled(1) or Disabled (0)"
    ::= {psAlarms1Masks 201}

a1VBV43Alarm OBJECT-TYPE
    SYNTAX   INTEGER{disabled(0), enabled(1)}
    MAX-ACCESS  read-write
    STATUS   current
    DESCRIPTION "Alarm of rectifier43 Enabled(1) or Disabled (0)"
    ::= {psAlarms1Masks 202}

a1VBV44Alarm OBJECT-TYPE
    SYNTAX   INTEGER{disabled(0), enabled(1)}
    MAX-ACCESS  read-write
    STATUS   current
    DESCRIPTION "Alarm of rectifier44 Enabled(1) or Disabled (0)"
    ::= {psAlarms1Masks 203}

a1VBV45Alarm OBJECT-TYPE
    SYNTAX   INTEGER{disabled(0), enabled(1)}
    MAX-ACCESS  read-write
    STATUS   current
    DESCRIPTION "Alarm of rectifier45 Enabled(1) or Disabled (0)"
    ::= {psAlarms1Masks 204}

a1VBV46Alarm OBJECT-TYPE
    SYNTAX   INTEGER{disabled(0), enabled(1)}
    MAX-ACCESS  read-write
    STATUS   current
    DESCRIPTION "Alarm of rectifier46 Enabled(1) or Disabled (0)"
    ::= {psAlarms1Masks 205}

a1VBV47Alarm OBJECT-TYPE
    SYNTAX   INTEGER{disabled(0), enabled(1)}
    MAX-ACCESS  read-write
    STATUS   current
    DESCRIPTION "Alarm of rectifier47 Enabled(1) or Disabled (0)"
    ::= {psAlarms1Masks 206}

a1VBV48Alarm OBJECT-TYPE
    SYNTAX   INTEGER{disabled(0), enabled(1)}
    MAX-ACCESS  read-write
    STATUS   current
    DESCRIPTION "Alarm of rectifier48 Enabled(1) or Disabled (0)"
    ::= {psAlarms1Masks 207}

a1VBV49Alarm OBJECT-TYPE
    SYNTAX   INTEGER{disabled(0), enabled(1)}
    MAX-ACCESS  read-write
    STATUS   current
    DESCRIPTION "Alarm of rectifier49 Enabled(1) or Disabled (0)"
    ::= {psAlarms1Masks 208}

a1VBV50Alarm OBJECT-TYPE
    SYNTAX   INTEGER{disabled(0), enabled(1)}
    MAX-ACCESS  read-write
    STATUS   current
    DESCRIPTION "Alarm of rectifier50 Enabled(1) or Disabled (0)"
    ::= {psAlarms1Masks 209}

a1VBV51Alarm OBJECT-TYPE
    SYNTAX   INTEGER{disabled(0), enabled(1)}
    MAX-ACCESS  read-write
    STATUS   current
    DESCRIPTION "Alarm of rectifier51 Enabled(1) or Disabled (0)"
    ::= {psAlarms1Masks 210}

a1VBV52Alarm OBJECT-TYPE
    SYNTAX   INTEGER{disabled(0), enabled(1)}
    MAX-ACCESS  read-write
    STATUS   current
    DESCRIPTION "Alarm of rectifier52 Enabled(1) or Disabled (0)"
    ::= {psAlarms1Masks 211}

a1VBV53Alarm OBJECT-TYPE
    SYNTAX   INTEGER{disabled(0), enabled(1)}
    MAX-ACCESS  read-write
    STATUS   current
    DESCRIPTION "Alarm of rectifier53 Enabled(1) or Disabled (0)"
    ::= {psAlarms1Masks 212}

a1VBV54Alarm OBJECT-TYPE
    SYNTAX   INTEGER{disabled(0), enabled(1)}
    MAX-ACCESS  read-write
    STATUS   current
    DESCRIPTION "Alarm of rectifier54 Enabled(1) or Disabled (0)"
    ::= {psAlarms1Masks 213}

a1VBV55Alarm OBJECT-TYPE
    SYNTAX   INTEGER{disabled(0), enabled(1)}
    MAX-ACCESS  read-write
    STATUS   current
    DESCRIPTION "Alarm of rectifier55 Enabled(1) or Disabled (0)"
    ::= {psAlarms1Masks 214}

a1VBV56Alarm OBJECT-TYPE
    SYNTAX   INTEGER{disabled(0), enabled(1)}
    MAX-ACCESS  read-write
    STATUS   current
    DESCRIPTION "Alarm of rectifier56 Enabled(1) or Disabled (0)"
    ::= {psAlarms1Masks 215}

a1VBV57Alarm OBJECT-TYPE
    SYNTAX   INTEGER{disabled(0), enabled(1)}
    MAX-ACCESS  read-write
    STATUS   current
    DESCRIPTION "Alarm of rectifier57 Enabled(1) or Disabled (0)"
    ::= {psAlarms1Masks 216}

a1VBV58Alarm OBJECT-TYPE
    SYNTAX   INTEGER{disabled(0), enabled(1)}
    MAX-ACCESS  read-write
    STATUS   current
    DESCRIPTION "Alarm of rectifier58 Enabled(1) or Disabled (0)"
    ::= {psAlarms1Masks 217}

a1VBV59Alarm OBJECT-TYPE
    SYNTAX   INTEGER{disabled(0), enabled(1)}
    MAX-ACCESS  read-write
    STATUS   current
    DESCRIPTION "Alarm of rectifier59 Enabled(1) or Disabled (0)"
    ::= {psAlarms1Masks 218}

a1VBV60Alarm OBJECT-TYPE
    SYNTAX   INTEGER{disabled(0), enabled(1)}
    MAX-ACCESS  read-write
    STATUS   current
    DESCRIPTION "Alarm of rectifier60 Enabled(1) or Disabled (0)"
    ::= {psAlarms1Masks 219}

a1VBV61Alarm OBJECT-TYPE
    SYNTAX   INTEGER{disabled(0), enabled(1)}
    MAX-ACCESS  read-write
    STATUS   current
    DESCRIPTION "Alarm of rectifier61 Enabled(1) or Disabled (0)"
    ::= {psAlarms1Masks 220}

a1VBV62Alarm OBJECT-TYPE
    SYNTAX   INTEGER{disabled(0), enabled(1)}
    MAX-ACCESS  read-write
    STATUS   current
    DESCRIPTION "Alarm of rectifier62 Enabled(1) or Disabled (0)"
    ::= {psAlarms1Masks 221}

a1VBV63Alarm OBJECT-TYPE
    SYNTAX   INTEGER{disabled(0), enabled(1)}
    MAX-ACCESS  read-write
    STATUS   current
    DESCRIPTION "Alarm of rectifier63 Enabled(1) or Disabled (0)"
    ::= {psAlarms1Masks 222}

a1VBV64Alarm OBJECT-TYPE
    SYNTAX   INTEGER{disabled(0), enabled(1)}
    MAX-ACCESS  read-write
    STATUS   current
    DESCRIPTION "Alarm of rectifier64 Enabled(1) or Disabled (0)"
    ::= {psAlarms1Masks 223}

a1VBV65Alarm OBJECT-TYPE
    SYNTAX   INTEGER{disabled(0), enabled(1)}
    MAX-ACCESS  read-write
    STATUS   current
    DESCRIPTION "Alarm of rectifier65 Enabled(1) or Disabled (0)"
    ::= {psAlarms1Masks 224}

a1VBV66Alarm OBJECT-TYPE
    SYNTAX   INTEGER{disabled(0), enabled(1)}
    MAX-ACCESS  read-write
    STATUS   current
    DESCRIPTION "Alarm of rectifier66 Enabled(1) or Disabled (0)"
    ::= {psAlarms1Masks 225}

a1VBV67Alarm OBJECT-TYPE
    SYNTAX   INTEGER{disabled(0), enabled(1)}
    MAX-ACCESS  read-write
    STATUS   current
    DESCRIPTION "Alarm of rectifier67 Enabled(1) or Disabled (0)"
    ::= {psAlarms1Masks 226}

a1VBV68Alarm OBJECT-TYPE
    SYNTAX   INTEGER{disabled(0), enabled(1)}
    MAX-ACCESS  read-write
    STATUS   current
    DESCRIPTION "Alarm of rectifier68 Enabled(1) or Disabled (0)"
    ::= {psAlarms1Masks 227}

a1VBV69Alarm OBJECT-TYPE
    SYNTAX   INTEGER{disabled(0), enabled(1)}
    MAX-ACCESS  read-write
    STATUS   current
    DESCRIPTION "Alarm of rectifier69 Enabled(1) or Disabled (0)"
    ::= {psAlarms1Masks 228}

a1VBV70Alarm OBJECT-TYPE
    SYNTAX   INTEGER{disabled(0), enabled(1)}
    MAX-ACCESS  read-write
    STATUS   current
    DESCRIPTION "Alarm of rectifier70 Enabled(1) or Disabled (0)"
    ::= {psAlarms1Masks 229}

a1VBV71Alarm OBJECT-TYPE
    SYNTAX   INTEGER{disabled(0), enabled(1)}
    MAX-ACCESS  read-write
    STATUS   current
    DESCRIPTION "Alarm of rectifier71 Enabled(1) or Disabled (0)"
    ::= {psAlarms1Masks 230}

a1VBV72Alarm OBJECT-TYPE
    SYNTAX   INTEGER{disabled(0), enabled(1)}
    MAX-ACCESS  read-write
    STATUS   current
    DESCRIPTION "Alarm of rectifier72 Enabled(1) or Disabled (0)"
    ::= {psAlarms1Masks 231}

a1VBV73Alarm OBJECT-TYPE
    SYNTAX   INTEGER{disabled(0), enabled(1)}
    MAX-ACCESS  read-write
    STATUS   current
    DESCRIPTION "Alarm of rectifier73 Enabled(1) or Disabled (0)"
    ::= {psAlarms1Masks 232}

a1VBV74Alarm OBJECT-TYPE
    SYNTAX   INTEGER{disabled(0), enabled(1)}
    MAX-ACCESS  read-write
    STATUS   current
    DESCRIPTION "Alarm of rectifier74 Enabled(1) or Disabled (0)"
    ::= {psAlarms1Masks 233}

a1VBV75Alarm OBJECT-TYPE
    SYNTAX   INTEGER{disabled(0), enabled(1)}
    MAX-ACCESS  read-write
    STATUS   current
    DESCRIPTION "Alarm of rectifier75 Enabled(1) or Disabled (0)"
    ::= {psAlarms1Masks 234}

a1VBV76Alarm OBJECT-TYPE
    SYNTAX   INTEGER{disabled(0), enabled(1)}
    MAX-ACCESS  read-write
    STATUS   current
    DESCRIPTION "Alarm of rectifier76 Enabled(1) or Disabled (0)"
    ::= {psAlarms1Masks 235}

a1VBV77Alarm OBJECT-TYPE
    SYNTAX   INTEGER{disabled(0), enabled(1)}
    MAX-ACCESS  read-write
    STATUS   current
    DESCRIPTION "Alarm of rectifier77 Enabled(1) or Disabled (0)"
    ::= {psAlarms1Masks 236}

a1VBV78Alarm OBJECT-TYPE
    SYNTAX   INTEGER{disabled(0), enabled(1)}
    MAX-ACCESS  read-write
    STATUS   current
    DESCRIPTION "Alarm of rectifier78 Enabled(1) or Disabled (0)"
    ::= {psAlarms1Masks 237}

a1VBV79Alarm OBJECT-TYPE
    SYNTAX   INTEGER{disabled(0), enabled(1)}
    MAX-ACCESS  read-write
    STATUS   current
    DESCRIPTION "Alarm of rectifier79 Enabled(1) or Disabled (0)"
    ::= {psAlarms1Masks 238}

a1VBV80Alarm OBJECT-TYPE
    SYNTAX   INTEGER{disabled(0), enabled(1)}
    MAX-ACCESS  read-write
    STATUS   current
    DESCRIPTION "Alarm of rectifier80 Enabled(1) or Disabled (0)"
    ::= {psAlarms1Masks 239}

a1VBV81Alarm OBJECT-TYPE
    SYNTAX   INTEGER{disabled(0), enabled(1)}
    MAX-ACCESS  read-write
    STATUS   current
    DESCRIPTION "Alarm of rectifier81 Enabled(1) or Disabled (0)"
    ::= {psAlarms1Masks 240}

a1VBV82Alarm OBJECT-TYPE
    SYNTAX   INTEGER{disabled(0), enabled(1)}
    MAX-ACCESS  read-write
    STATUS   current
    DESCRIPTION "Alarm of rectifier82 Enabled(1) or Disabled (0)"
    ::= {psAlarms1Masks 241}

a1VBV83Alarm OBJECT-TYPE
    SYNTAX   INTEGER{disabled(0), enabled(1)}
    MAX-ACCESS  read-write
    STATUS   current
    DESCRIPTION "Alarm of rectifier83 Enabled(1) or Disabled (0)"
    ::= {psAlarms1Masks 242}

a1VBV84Alarm OBJECT-TYPE
    SYNTAX   INTEGER{disabled(0), enabled(1)}
    MAX-ACCESS  read-write
    STATUS   current
    DESCRIPTION "Alarm of rectifier84 Enabled(1) or Disabled (0)"
    ::= {psAlarms1Masks 243}

a1VBV85Alarm OBJECT-TYPE
    SYNTAX   INTEGER{disabled(0), enabled(1)}
    MAX-ACCESS  read-write
    STATUS   current
    DESCRIPTION "Alarm of rectifier85 Enabled(1) or Disabled (0)"
    ::= {psAlarms1Masks 244}

a1VBV86Alarm OBJECT-TYPE
    SYNTAX   INTEGER{disabled(0), enabled(1)}
    MAX-ACCESS  read-write
    STATUS   current
    DESCRIPTION "Alarm of rectifier86 Enabled(1) or Disabled (0)"
    ::= {psAlarms1Masks 245}

a1VBV87Alarm OBJECT-TYPE
    SYNTAX   INTEGER{disabled(0), enabled(1)}
    MAX-ACCESS  read-write
    STATUS   current
    DESCRIPTION "Alarm of rectifier87 Enabled(1) or Disabled (0)"
    ::= {psAlarms1Masks 246}

a1VBV88Alarm OBJECT-TYPE
    SYNTAX   INTEGER{disabled(0), enabled(1)}
    MAX-ACCESS  read-write
    STATUS   current
    DESCRIPTION "Alarm of rectifier88 Enabled(1) or Disabled (0)"
    ::= {psAlarms1Masks 247}

a1VBV89Alarm OBJECT-TYPE
    SYNTAX   INTEGER{disabled(0), enabled(1)}
    MAX-ACCESS  read-write
    STATUS   current
    DESCRIPTION "Alarm of rectifier89 Enabled(1) or Disabled (0)"
    ::= {psAlarms1Masks 248}

a1VBV90Alarm OBJECT-TYPE
    SYNTAX   INTEGER{disabled(0), enabled(1)}
    MAX-ACCESS  read-write
    STATUS   current
    DESCRIPTION "Alarm of rectifier90 Enabled(1) or Disabled (0)"
    ::= {psAlarms1Masks 249}

a1VBV91Alarm OBJECT-TYPE
    SYNTAX   INTEGER{disabled(0), enabled(1)}
    MAX-ACCESS  read-write
    STATUS   current
    DESCRIPTION "Alarm of rectifier91 Enabled(1) or Disabled (0)"
    ::= {psAlarms1Masks 250}

a1VBV92Alarm OBJECT-TYPE
    SYNTAX   INTEGER{disabled(0), enabled(1)}
    MAX-ACCESS  read-write
    STATUS   current
    DESCRIPTION "Alarm of rectifier92 Enabled(1) or Disabled (0)"
    ::= {psAlarms1Masks 251}

a1VBV93Alarm OBJECT-TYPE
    SYNTAX   INTEGER{disabled(0), enabled(1)}
    MAX-ACCESS  read-write
    STATUS   current
    DESCRIPTION "Alarm of rectifier93 Enabled(1) or Disabled (0)"
    ::= {psAlarms1Masks 252}

a1VBV94Alarm OBJECT-TYPE
    SYNTAX   INTEGER{disabled(0), enabled(1)}
    MAX-ACCESS  read-write
    STATUS   current
    DESCRIPTION "Alarm of rectifier94 Enabled(1) or Disabled (0)"
    ::= {psAlarms1Masks 253}

a1VBV95Alarm OBJECT-TYPE
    SYNTAX   INTEGER{disabled(0), enabled(1)}
    MAX-ACCESS  read-write
    STATUS   current
    DESCRIPTION "Alarm of rectifier95 Enabled(1) or Disabled (0)"
    ::= {psAlarms1Masks 254}

a1VBV96Alarm OBJECT-TYPE
    SYNTAX   INTEGER{disabled(0), enabled(1)}
    MAX-ACCESS  read-write
    STATUS   current
    DESCRIPTION "Alarm of rectifier96 Enabled(1) or Disabled (0)"
    ::= {psAlarms1Masks 255}

a1VBV97Alarm OBJECT-TYPE
    SYNTAX   INTEGER{disabled(0), enabled(1)}
    MAX-ACCESS  read-write
    STATUS   current
    DESCRIPTION "Alarm of rectifier97 Enabled(1) or Disabled (0)"
    ::= {psAlarms1Masks 256}

a1VBV98Alarm OBJECT-TYPE
    SYNTAX   INTEGER{disabled(0), enabled(1)}
    MAX-ACCESS  read-write
    STATUS   current
    DESCRIPTION "Alarm of rectifier98 Enabled(1) or Disabled (0)"
    ::= {psAlarms1Masks 257}

a1VBV99Alarm OBJECT-TYPE
    SYNTAX   INTEGER{disabled(0), enabled(1)}
    MAX-ACCESS  read-write
    STATUS   current
    DESCRIPTION "Alarm of rectifier99 Enabled(1) or Disabled (0)"
    ::= {psAlarms1Masks 258}

a1VBV100Alarm OBJECT-TYPE
    SYNTAX   INTEGER{disabled(0), enabled(1)}
    MAX-ACCESS  read-write
    STATUS   current
    DESCRIPTION "Alarm of rectifier100 Enabled(1) or Disabled (0)"
    ::= {psAlarms1Masks 259}

a1VBV101Alarm OBJECT-TYPE
    SYNTAX   INTEGER{disabled(0), enabled(1)}
    MAX-ACCESS  read-write
    STATUS   current
    DESCRIPTION "Alarm of rectifier101 Enabled(1) or Disabled (0)"
    ::= {psAlarms1Masks 260}

a1VBV102Alarm OBJECT-TYPE
    SYNTAX   INTEGER{disabled(0), enabled(1)}
    MAX-ACCESS  read-write
    STATUS   current
    DESCRIPTION "Alarm of rectifier102 Enabled(1) or Disabled (0)"
    ::= {psAlarms1Masks 261}

a1VBV103Alarm OBJECT-TYPE
    SYNTAX   INTEGER{disabled(0), enabled(1)}
    MAX-ACCESS  read-write
    STATUS   current
    DESCRIPTION "Alarm of rectifier103 Enabled(1) or Disabled (0)"
    ::= {psAlarms1Masks 262}

a1VBV104Alarm OBJECT-TYPE
    SYNTAX   INTEGER{disabled(0), enabled(1)}
    MAX-ACCESS  read-write
    STATUS   current
    DESCRIPTION "Alarm of rectifier104 Enabled(1) or Disabled (0)"
    ::= {psAlarms1Masks 263}

a1VBV105Alarm OBJECT-TYPE
    SYNTAX   INTEGER{disabled(0), enabled(1)}
    MAX-ACCESS  read-write
    STATUS   current
    DESCRIPTION "Alarm of rectifier105 Enabled(1) or Disabled (0)"
    ::= {psAlarms1Masks 264}

a1VBV106Alarm OBJECT-TYPE
    SYNTAX   INTEGER{disabled(0), enabled(1)}
    MAX-ACCESS  read-write
    STATUS   current
    DESCRIPTION "Alarm of rectifier106 Enabled(1) or Disabled (0)"
    ::= {psAlarms1Masks 265}

a1VBV107Alarm OBJECT-TYPE
    SYNTAX   INTEGER{disabled(0), enabled(1)}
    MAX-ACCESS  read-write
    STATUS   current
    DESCRIPTION "Alarm of rectifier107 Enabled(1) or Disabled (0)"
    ::= {psAlarms1Masks 266}

a1VBV108Alarm OBJECT-TYPE
    SYNTAX   INTEGER{disabled(0), enabled(1)}
    MAX-ACCESS  read-write
    STATUS   current
    DESCRIPTION "Alarm of rectifier108 Enabled(1) or Disabled (0)"
    ::= {psAlarms1Masks 267}

a1VBV109Alarm OBJECT-TYPE
    SYNTAX   INTEGER{disabled(0), enabled(1)}
    MAX-ACCESS  read-write
    STATUS   current
    DESCRIPTION "Alarm of rectifier109 Enabled(1) or Disabled (0)"
    ::= {psAlarms1Masks 268}

a1VBV110Alarm OBJECT-TYPE
    SYNTAX   INTEGER{disabled(0), enabled(1)}
    MAX-ACCESS  read-write
    STATUS   current
    DESCRIPTION "Alarm of rectifier110 Enabled(1) or Disabled (0)"
    ::= {psAlarms1Masks 269}

a1VBV111Alarm OBJECT-TYPE
    SYNTAX   INTEGER{disabled(0), enabled(1)}
    MAX-ACCESS  read-write
    STATUS   current
    DESCRIPTION "Alarm of rectifier111 Enabled(1) or Disabled (0)"
    ::= {psAlarms1Masks 270}

a1VBV112Alarm OBJECT-TYPE
    SYNTAX   INTEGER{disabled(0), enabled(1)}
    MAX-ACCESS  read-write
    STATUS   current
    DESCRIPTION "Alarm of rectifier112 Enabled(1) or Disabled (0)"
    ::= {psAlarms1Masks 271}

a1VBV113Alarm OBJECT-TYPE
    SYNTAX   INTEGER{disabled(0), enabled(1)}
    MAX-ACCESS  read-write
    STATUS   current
    DESCRIPTION "Alarm of rectifier113 Enabled(1) or Disabled (0)"
    ::= {psAlarms1Masks 272}

a1VBV114Alarm OBJECT-TYPE
    SYNTAX   INTEGER{disabled(0), enabled(1)}
    MAX-ACCESS  read-write
    STATUS   current
    DESCRIPTION "Alarm of rectifier114 Enabled(1) or Disabled (0)"
    ::= {psAlarms1Masks 273}

a1VBV115Alarm OBJECT-TYPE
    SYNTAX   INTEGER{disabled(0), enabled(1)}
    MAX-ACCESS  read-write
    STATUS   current
    DESCRIPTION "Alarm of rectifier115 Enabled(1) or Disabled (0)"
    ::= {psAlarms1Masks 274}

a1VBV116Alarm OBJECT-TYPE
    SYNTAX   INTEGER{disabled(0), enabled(1)}
    MAX-ACCESS  read-write
    STATUS   current
    DESCRIPTION "Alarm of rectifier116 Enabled(1) or Disabled (0)"
    ::= {psAlarms1Masks 275}

a1VBV117Alarm OBJECT-TYPE
    SYNTAX   INTEGER{disabled(0), enabled(1)}
    MAX-ACCESS  read-write
    STATUS   current
    DESCRIPTION "Alarm of rectifier117 Enabled(1) or Disabled (0)"
    ::= {psAlarms1Masks 276}

a1VBV118Alarm OBJECT-TYPE
    SYNTAX   INTEGER{disabled(0), enabled(1)}
    MAX-ACCESS  read-write
    STATUS   current
    DESCRIPTION "Alarm of rectifier118 Enabled(1) or Disabled (0)"
    ::= {psAlarms1Masks 277}

a1VBV119Alarm OBJECT-TYPE
    SYNTAX   INTEGER{disabled(0), enabled(1)}
    MAX-ACCESS  read-write
    STATUS   current
    DESCRIPTION "Alarm of rectifier119 Enabled(1) or Disabled (0)"
    ::= {psAlarms1Masks 278}

a1VBV120Alarm OBJECT-TYPE
    SYNTAX   INTEGER{disabled(0), enabled(1)}
    MAX-ACCESS  read-write
    STATUS   current
    DESCRIPTION "Alarm of rectifier120 Enabled(1) or Disabled (0)"
    ::= {psAlarms1Masks 279}

a1VBV121Alarm OBJECT-TYPE
    SYNTAX   INTEGER{disabled(0), enabled(1)}
    MAX-ACCESS  read-write
    STATUS   current
    DESCRIPTION "Alarm of rectifier121 Enabled(1) or Disabled (0)"
    ::= {psAlarms1Masks 280}

a1VBV122Alarm OBJECT-TYPE
    SYNTAX   INTEGER{disabled(0), enabled(1)}
    MAX-ACCESS  read-write
    STATUS   current
    DESCRIPTION "Alarm of rectifier122 Enabled(1) or Disabled (0)"
    ::= {psAlarms1Masks 281}

a1VBV123Alarm OBJECT-TYPE
    SYNTAX   INTEGER{disabled(0), enabled(1)}
    MAX-ACCESS  read-write
    STATUS   current
    DESCRIPTION "Alarm of rectifier123 Enabled(1) or Disabled (0)"
    ::= {psAlarms1Masks 282}

a1VBV124Alarm OBJECT-TYPE
    SYNTAX   INTEGER{disabled(0), enabled(1)}
    MAX-ACCESS  read-write
    STATUS   current
    DESCRIPTION "Alarm of rectifier124 Enabled(1) or Disabled (0)"
    ::= {psAlarms1Masks 283}

a1VBV125Alarm OBJECT-TYPE
    SYNTAX   INTEGER{disabled(0), enabled(1)}
    MAX-ACCESS  read-write
    STATUS   current
    DESCRIPTION "Alarm of rectifier125 Enabled(1) or Disabled (0)"
    ::= {psAlarms1Masks 284}

a1VBV126Alarm OBJECT-TYPE
    SYNTAX   INTEGER{disabled(0), enabled(1)}
    MAX-ACCESS  read-write
    STATUS   current
    DESCRIPTION "Alarm of rectifier126 Enabled(1) or Disabled (0)"
    ::= {psAlarms1Masks 285}

a1VBV127Alarm OBJECT-TYPE
    SYNTAX   INTEGER{disabled(0), enabled(1)}
    MAX-ACCESS  read-write
    STATUS   current
    DESCRIPTION "Alarm of rectifier127 Enabled(1) or Disabled (0)"
    ::= {psAlarms1Masks 286}

a1VBV128Alarm OBJECT-TYPE
    SYNTAX   INTEGER{disabled(0), enabled(1)}
    MAX-ACCESS  read-write
    STATUS   current
    DESCRIPTION "Alarm of rectifier128 Enabled(1) or Disabled (0)"
    ::= {psAlarms1Masks 287}

a1VBV129Alarm OBJECT-TYPE
    SYNTAX   INTEGER{disabled(0), enabled(1)}
    MAX-ACCESS  read-write
    STATUS   current
    DESCRIPTION "Alarm of rectifier129 Enabled(1) or Disabled (0)"
    ::= {psAlarms1Masks 288}

a1VBV130Alarm OBJECT-TYPE
    SYNTAX   INTEGER{disabled(0), enabled(1)}
    MAX-ACCESS  read-write
    STATUS   current
    DESCRIPTION "Alarm of rectifier130 Enabled(1) or Disabled (0)"
    ::= {psAlarms1Masks 289}

a1VBV131Alarm OBJECT-TYPE
    SYNTAX   INTEGER{disabled(0), enabled(1)}
    MAX-ACCESS  read-write
    STATUS   current
    DESCRIPTION "Alarm of rectifier131 Enabled(1) or Disabled (0)"
    ::= {psAlarms1Masks 290}

a1VBV132Alarm OBJECT-TYPE
    SYNTAX   INTEGER{disabled(0), enabled(1)}
    MAX-ACCESS  read-write
    STATUS   current
    DESCRIPTION "Alarm of rectifier132 Enabled(1) or Disabled (0)"
    ::= {psAlarms1Masks 291}

a1VBV133Alarm OBJECT-TYPE
    SYNTAX   INTEGER{disabled(0), enabled(1)}
    MAX-ACCESS  read-write
    STATUS   current
    DESCRIPTION "Alarm of rectifier133 Enabled(1) or Disabled (0)"
    ::= {psAlarms1Masks 292}

a1VBV134Alarm OBJECT-TYPE
    SYNTAX   INTEGER{disabled(0), enabled(1)}
    MAX-ACCESS  read-write
    STATUS   current
    DESCRIPTION "Alarm of rectifier134 Enabled(1) or Disabled (0)"
    ::= {psAlarms1Masks 293}

a1VBV135Alarm OBJECT-TYPE
    SYNTAX   INTEGER{disabled(0), enabled(1)}
    MAX-ACCESS  read-write
    STATUS   current
    DESCRIPTION "Alarm of rectifier135 Enabled(1) or Disabled (0)"
    ::= {psAlarms1Masks 294}

a1VBV136Alarm OBJECT-TYPE
    SYNTAX   INTEGER{disabled(0), enabled(1)}
    MAX-ACCESS  read-write
    STATUS   current
    DESCRIPTION "Alarm of rectifier136 Enabled(1) or Disabled (0)"
    ::= {psAlarms1Masks 295}

a1VBV137Alarm OBJECT-TYPE
    SYNTAX   INTEGER{disabled(0), enabled(1)}
    MAX-ACCESS  read-write
    STATUS   current
    DESCRIPTION "Alarm of rectifier137 Enabled(1) or Disabled (0)"
    ::= {psAlarms1Masks 296}

a1VBV138Alarm OBJECT-TYPE
    SYNTAX   INTEGER{disabled(0), enabled(1)}
    MAX-ACCESS  read-write
    STATUS   current
    DESCRIPTION "Alarm of rectifier138 Enabled(1) or Disabled (0)"
    ::= {psAlarms1Masks 297}

a1VBV139Alarm OBJECT-TYPE
    SYNTAX   INTEGER{disabled(0), enabled(1)}
    MAX-ACCESS  read-write
    STATUS   current
    DESCRIPTION "Alarm of rectifier139 Enabled(1) or Disabled (0)"
    ::= {psAlarms1Masks 298}

a1VBV140Alarm OBJECT-TYPE
    SYNTAX   INTEGER{disabled(0), enabled(1)}
    MAX-ACCESS  read-write
    STATUS   current
    DESCRIPTION "Alarm of rectifier140 Enabled(1) or Disabled (0)"
    ::= {psAlarms1Masks 299}

a1VBV141Alarm OBJECT-TYPE
    SYNTAX   INTEGER{disabled(0), enabled(1)}
    MAX-ACCESS  read-write
    STATUS   current
    DESCRIPTION "Alarm of rectifier141 Enabled(1) or Disabled (0)"
    ::= {psAlarms1Masks 300}

a1VBV142Alarm OBJECT-TYPE
    SYNTAX   INTEGER{disabled(0), enabled(1)}
    MAX-ACCESS  read-write
    STATUS   current
    DESCRIPTION "Alarm of rectifier142 Enabled(1) or Disabled (0)"
    ::= {psAlarms1Masks 301}

a1VBV143Alarm OBJECT-TYPE
    SYNTAX   INTEGER{disabled(0), enabled(1)}
    MAX-ACCESS  read-write
    STATUS   current
    DESCRIPTION "Alarm of rectifier143 Enabled(1) or Disabled (0)"
    ::= {psAlarms1Masks 302}

a1VBV144Alarm OBJECT-TYPE
    SYNTAX   INTEGER{disabled(0), enabled(1)}
    MAX-ACCESS  read-write
    STATUS   current
    DESCRIPTION "Alarm of rectifier144 Enabled(1) or Disabled (0)"
    ::= {psAlarms1Masks 303}

a1VBV145Alarm OBJECT-TYPE
    SYNTAX   INTEGER{disabled(0), enabled(1)}
    MAX-ACCESS  read-write
    STATUS   current
    DESCRIPTION "Alarm of rectifier145 Enabled(1) or Disabled (0)"
    ::= {psAlarms1Masks 304}

a1VBV146Alarm OBJECT-TYPE
    SYNTAX   INTEGER{disabled(0), enabled(1)}
    MAX-ACCESS  read-write
    STATUS   current
    DESCRIPTION "Alarm of rectifier146 Enabled(1) or Disabled (0)"
    ::= {psAlarms1Masks 305}

a1VBV147Alarm OBJECT-TYPE
    SYNTAX   INTEGER{disabled(0), enabled(1)}
    MAX-ACCESS  read-write
    STATUS   current
    DESCRIPTION "Alarm of rectifier147 Enabled(1) or Disabled (0)"
    ::= {psAlarms1Masks 306}

a1VBV148Alarm OBJECT-TYPE
    SYNTAX   INTEGER{disabled(0), enabled(1)}
    MAX-ACCESS  read-write
    STATUS   current
    DESCRIPTION "Alarm of rectifier148 Enabled(1) or Disabled (0)"
    ::= {psAlarms1Masks 307}

a1VBV149Alarm OBJECT-TYPE
    SYNTAX   INTEGER{disabled(0), enabled(1)}
    MAX-ACCESS  read-write
    STATUS   current
    DESCRIPTION "Alarm of rectifier149 Enabled(1) or Disabled (0)"
    ::= {psAlarms1Masks 308}

a1VBV150Alarm OBJECT-TYPE
    SYNTAX   INTEGER{disabled(0), enabled(1)}
    MAX-ACCESS  read-write
    STATUS   current
    DESCRIPTION "Alarm of rectifier150 Enabled(1) or Disabled (0)"
    ::= {psAlarms1Masks 309}

a1VBV151Alarm OBJECT-TYPE
    SYNTAX   INTEGER{disabled(0), enabled(1)}
    MAX-ACCESS  read-write
    STATUS   current
    DESCRIPTION "Alarm of rectifier151 Enabled(1) or Disabled (0)"
    ::= {psAlarms1Masks 310}

a1VBV152Alarm OBJECT-TYPE
    SYNTAX   INTEGER{disabled(0), enabled(1)}
    MAX-ACCESS  read-write
    STATUS   current
    DESCRIPTION "Alarm of rectifier152 Enabled(1) or Disabled (0)"
    ::= {psAlarms1Masks 311}

a1VBV153Alarm OBJECT-TYPE
    SYNTAX   INTEGER{disabled(0), enabled(1)}
    MAX-ACCESS  read-write
    STATUS   current
    DESCRIPTION "Alarm of rectifier153 Enabled(1) or Disabled (0)"
    ::= {psAlarms1Masks 312}

a1VBV154Alarm OBJECT-TYPE
    SYNTAX   INTEGER{disabled(0), enabled(1)}
    MAX-ACCESS  read-write
    STATUS   current
    DESCRIPTION "Alarm of rectifier154 Enabled(1) or Disabled (0)"
    ::= {psAlarms1Masks 313}

a1VBV155Alarm OBJECT-TYPE
    SYNTAX   INTEGER{disabled(0), enabled(1)}
    MAX-ACCESS  read-write
    STATUS   current
    DESCRIPTION "Alarm of rectifier155 Enabled(1) or Disabled (0)"
    ::= {psAlarms1Masks 314}

a1VBV156Alarm OBJECT-TYPE
    SYNTAX   INTEGER{disabled(0), enabled(1)}
    MAX-ACCESS  read-write
    STATUS   current
    DESCRIPTION "Alarm of rectifier156 Enabled(1) or Disabled (0)"
    ::= {psAlarms1Masks 315}

a1VBV157Alarm OBJECT-TYPE
    SYNTAX   INTEGER{disabled(0), enabled(1)}
    MAX-ACCESS  read-write
    STATUS   current
    DESCRIPTION "Alarm of rectifier157 Enabled(1) or Disabled (0)"
    ::= {psAlarms1Masks 316}

a1VBV158Alarm OBJECT-TYPE
    SYNTAX   INTEGER{disabled(0), enabled(1)}
    MAX-ACCESS  read-write
    STATUS   current
    DESCRIPTION "Alarm of rectifier158 Enabled(1) or Disabled (0)"
    ::= {psAlarms1Masks 317}

a1VBV159Alarm OBJECT-TYPE
    SYNTAX   INTEGER{disabled(0), enabled(1)}
    MAX-ACCESS  read-write
    STATUS   current
    DESCRIPTION "Alarm of rectifier159 Enabled(1) or Disabled (0)"
    ::= {psAlarms1Masks 318}

a1VBV160Alarm OBJECT-TYPE
    SYNTAX   INTEGER{disabled(0), enabled(1)}
    MAX-ACCESS  read-write
    STATUS   current
    DESCRIPTION "Alarm of rectifier160 Enabled(1) or Disabled (0)"
    ::= {psAlarms1Masks 319}

a1VBV161Alarm OBJECT-TYPE
    SYNTAX   INTEGER{disabled(0), enabled(1)}
    MAX-ACCESS  read-write
    STATUS   current
    DESCRIPTION "Alarm of rectifier161 Enabled(1) or Disabled (0)"
    ::= {psAlarms1Masks 320}

a1VBV162Alarm OBJECT-TYPE
    SYNTAX   INTEGER{disabled(0), enabled(1)}
    MAX-ACCESS  read-write
    STATUS   current
    DESCRIPTION "Alarm of rectifier162 Enabled(1) or Disabled (0)"
    ::= {psAlarms1Masks 321}

a1VBV163Alarm OBJECT-TYPE
    SYNTAX   INTEGER{disabled(0), enabled(1)}
    MAX-ACCESS  read-write
    STATUS   current
    DESCRIPTION "Alarm of rectifier163 Enabled(1) or Disabled (0)"
    ::= {psAlarms1Masks 322}

a1VBV164Alarm OBJECT-TYPE
    SYNTAX   INTEGER{disabled(0), enabled(1)}
    MAX-ACCESS  read-write
    STATUS   current
    DESCRIPTION "Alarm of rectifier164 Enabled(1) or Disabled (0)"
    ::= {psAlarms1Masks 323}

a1VBV165Alarm OBJECT-TYPE
    SYNTAX   INTEGER{disabled(0), enabled(1)}
    MAX-ACCESS  read-write
    STATUS   current
    DESCRIPTION "Alarm of rectifier165 Enabled(1) or Disabled (0)"
    ::= {psAlarms1Masks 324}

a1VBV166Alarm OBJECT-TYPE
    SYNTAX   INTEGER{disabled(0), enabled(1)}
    MAX-ACCESS  read-write
    STATUS   current
    DESCRIPTION "Alarm of rectifier166 Enabled(1) or Disabled (0)"
    ::= {psAlarms1Masks 325}

a1VBV167Alarm OBJECT-TYPE
    SYNTAX   INTEGER{disabled(0), enabled(1)}
    MAX-ACCESS  read-write
    STATUS   current
    DESCRIPTION "Alarm of rectifier167 Enabled(1) or Disabled (0)"
    ::= {psAlarms1Masks 326}

a1VBV168Alarm OBJECT-TYPE
    SYNTAX   INTEGER{disabled(0), enabled(1)}
    MAX-ACCESS  read-write
    STATUS   current
    DESCRIPTION "Alarm of rectifier168 Enabled(1) or Disabled (0)"
    ::= {psAlarms1Masks 327}

a1VBV169Alarm OBJECT-TYPE
    SYNTAX   INTEGER{disabled(0), enabled(1)}
    MAX-ACCESS  read-write
    STATUS   current
    DESCRIPTION "Alarm of rectifier169 Enabled(1) or Disabled (0)"
    ::= {psAlarms1Masks 328}

a1VBV170Alarm OBJECT-TYPE
    SYNTAX   INTEGER{disabled(0), enabled(1)}
    MAX-ACCESS  read-write
    STATUS   current
    DESCRIPTION "Alarm of rectifier170 Enabled(1) or Disabled (0)"
    ::= {psAlarms1Masks 329}

a1VBV171Alarm OBJECT-TYPE
    SYNTAX   INTEGER{disabled(0), enabled(1)}
    MAX-ACCESS  read-write
    STATUS   current
    DESCRIPTION "Alarm of rectifier171 Enabled(1) or Disabled (0)"
    ::= {psAlarms1Masks 330}

a1VBV172Alarm OBJECT-TYPE
    SYNTAX   INTEGER{disabled(0), enabled(1)}
    MAX-ACCESS  read-write
    STATUS   current
    DESCRIPTION "Alarm of rectifier172 Enabled(1) or Disabled (0)"
    ::= {psAlarms1Masks 331}

a1VBV173Alarm OBJECT-TYPE
    SYNTAX   INTEGER{disabled(0), enabled(1)}
    MAX-ACCESS  read-write
    STATUS   current
    DESCRIPTION "Alarm of rectifier173 Enabled(1) or Disabled (0)"
    ::= {psAlarms1Masks 332}

a1VBV174Alarm OBJECT-TYPE
    SYNTAX   INTEGER{disabled(0), enabled(1)}
    MAX-ACCESS  read-write
    STATUS   current
    DESCRIPTION "Alarm of rectifier174 Enabled(1) or Disabled (0)"
    ::= {psAlarms1Masks 333}

a1VBV175Alarm OBJECT-TYPE
    SYNTAX   INTEGER{disabled(0), enabled(1)}
    MAX-ACCESS  read-write
    STATUS   current
    DESCRIPTION "Alarm of rectifier175 Enabled(1) or Disabled (0)"
    ::= {psAlarms1Masks 334}

a1VBV176Alarm OBJECT-TYPE
    SYNTAX   INTEGER{disabled(0), enabled(1)}
    MAX-ACCESS  read-write
    STATUS   current
    DESCRIPTION "Alarm of rectifier176 Enabled(1) or Disabled (0)"
    ::= {psAlarms1Masks 335}

a1VBV177Alarm OBJECT-TYPE
    SYNTAX   INTEGER{disabled(0), enabled(1)}
    MAX-ACCESS  read-write
    STATUS   current
    DESCRIPTION "Alarm of rectifier177 Enabled(1) or Disabled (0)"
    ::= {psAlarms1Masks 336}

a1VBV178Alarm OBJECT-TYPE
    SYNTAX   INTEGER{disabled(0), enabled(1)}
    MAX-ACCESS  read-write
    STATUS   current
    DESCRIPTION "Alarm of rectifier178 Enabled(1) or Disabled (0)"
    ::= {psAlarms1Masks 337}

a1VBV179Alarm OBJECT-TYPE
    SYNTAX   INTEGER{disabled(0), enabled(1)}
    MAX-ACCESS  read-write
    STATUS   current
    DESCRIPTION "Alarm of rectifier179 Enabled(1) or Disabled (0)"
    ::= {psAlarms1Masks 338}

a1VBV180Alarm OBJECT-TYPE
    SYNTAX   INTEGER{disabled(0), enabled(1)}
    MAX-ACCESS  read-write
    STATUS   current
    DESCRIPTION "Alarm of rectifier180 Enabled(1) or Disabled (0)"
    ::= {psAlarms1Masks 339}

a1VBVNoReserve OBJECT-TYPE
    SYNTAX   INTEGER{disabled(0), enabled(1)}
    MAX-ACCESS  read-write
    STATUS   current
    DESCRIPTION "Enabled(1) or Disabled (0)"
    ::= {psAlarms1Masks 340}

a1VBVHighEfficiency OBJECT-TYPE
    SYNTAX   INTEGER{disabled(0), enabled(1)}
    MAX-ACCESS  read-write
    STATUS   current
    DESCRIPTION "Enabled(1) or Disabled (0)"
    ::= {psAlarms1Masks 341}

--PhasesAlarm in psAlarms1Masks
a1Phase1Alarm OBJECT-TYPE
    SYNTAX   INTEGER{disabled(0), enabled(1)}
    MAX-ACCESS  read-write
    STATUS   current
    DESCRIPTION "Enabled(1) or Disabled (0)"
    ::= {psAlarms1Masks 352}

a1Phase2Alarm OBJECT-TYPE
    SYNTAX   INTEGER{disabled(0), enabled(1)}
    MAX-ACCESS  read-write
    STATUS   current
    DESCRIPTION "Enabled(1) or Disabled (0)"
    ::= {psAlarms1Masks 353}

a1Phase3Alarm OBJECT-TYPE
    SYNTAX   INTEGER{disabled(0), enabled(1)}
    MAX-ACCESS  read-write
    STATUS   current
    DESCRIPTION "Enabled(1) or Disabled (0)"
    ::= {psAlarms1Masks 354}

a1MainsSensorError OBJECT-TYPE
    SYNTAX   INTEGER{disabled(0), enabled(1)}
    MAX-ACCESS  read-write
    STATUS   current
    DESCRIPTION "Enabled(1) or Disabled (0)"
    ::= {psAlarms1Masks 355}

a1LightProtectionAlarm OBJECT-TYPE
    SYNTAX   INTEGER{disabled(0), enabled(1)}
    MAX-ACCESS  read-write
    STATUS   current
    DESCRIPTION "Enabled(1) or Disabled (0)"
    ::= {psAlarms1Masks 356}

--Ambience Temperature in psAlarms1Masks
a1LowTemperature OBJECT-TYPE
    SYNTAX   INTEGER{disabled(0), enabled(1)}
    MAX-ACCESS  read-write
    STATUS   current
    DESCRIPTION "Enabled(1) or Disabled (0)"
    ::= {psAlarms1Masks 384}

a1HighTemperature OBJECT-TYPE
    SYNTAX   INTEGER{disabled(0), enabled(1)}
    MAX-ACCESS  read-write
    STATUS   current
    DESCRIPTION "Enabled(1) or Disabled (0)"
    ::= {psAlarms1Masks 385}

a1TemperatureSensorError OBJECT-TYPE
    SYNTAX   INTEGER{disabled(0), enabled(1)}
    MAX-ACCESS  read-write
    STATUS   current
    DESCRIPTION "Enabled(1) or Disabled (0)"
    ::= {psAlarms1Masks 386}

--DryContacts in psAlarms1Masks
a1DryContact1 OBJECT-TYPE
    SYNTAX   INTEGER{disabled(0), enabled(1)}
    MAX-ACCESS  read-write
    STATUS   current
    DESCRIPTION "Enabled(1) or Disabled (0)"
    ::= {psAlarms1Masks 416}

a1DryContact2 OBJECT-TYPE
    SYNTAX   INTEGER{disabled(0), enabled(1)}
    MAX-ACCESS  read-write
    STATUS   current
    DESCRIPTION "Enabled(1) or Disabled (0)"
    ::= {psAlarms1Masks 417}

a1DryContact3 OBJECT-TYPE
    SYNTAX   INTEGER{disabled(0), enabled(1)}
    MAX-ACCESS  read-write
    STATUS   current
    DESCRIPTION "Enabled(1) or Disabled (0)"
    ::= {psAlarms1Masks 418}

a1DryContact4 OBJECT-TYPE
    SYNTAX   INTEGER{disabled(0), enabled(1)}
    MAX-ACCESS  read-write
    STATUS   current
    DESCRIPTION "Enabled(1) or Disabled (0)"
    ::= {psAlarms1Masks 419}

a1DryContact5 OBJECT-TYPE
    SYNTAX   INTEGER{disabled(0), enabled(1)}
    MAX-ACCESS  read-write
    STATUS   current
    DESCRIPTION "Enabled(1) or Disabled (0)"
    ::= {psAlarms1Masks 420}

a1DryContact6 OBJECT-TYPE
    SYNTAX   INTEGER{disabled(0), enabled(1)}
    MAX-ACCESS  read-write
    STATUS   current
    DESCRIPTION "Enabled(1) or Disabled (0)"
    ::= {psAlarms1Masks 421}

a1DryContact7 OBJECT-TYPE
    SYNTAX   INTEGER{disabled(0), enabled(1)}
    MAX-ACCESS  read-write
    STATUS   current
    DESCRIPTION "Enabled(1) or Disabled (0)"
    ::= {psAlarms1Masks 422}

a1DryContact8 OBJECT-TYPE
    SYNTAX   INTEGER{disabled(0), enabled(1)}
    MAX-ACCESS  read-write
    STATUS   current
    DESCRIPTION "Enabled(1) or Disabled (0)"
    ::= {psAlarms1Masks 423}

a1DryContact9 OBJECT-TYPE
    SYNTAX   INTEGER{disabled(0), enabled(1)}
    MAX-ACCESS  read-write
    STATUS   current
    DESCRIPTION "Enabled(1) or Disabled (0)"
    ::= {psAlarms1Masks 424}

a1DryContact10 OBJECT-TYPE
    SYNTAX   INTEGER{disabled(0), enabled(1)}
    MAX-ACCESS  read-write
    STATUS   current
    DESCRIPTION "Enabled(1) or Disabled (0)"
    ::= {psAlarms1Masks 425}

a1DryContact11 OBJECT-TYPE
    SYNTAX   INTEGER{disabled(0), enabled(1)}
    MAX-ACCESS  read-write
    STATUS   current
    DESCRIPTION "Enabled(1) or Disabled (0)"
    ::= {psAlarms1Masks 426}

a1DryContact12 OBJECT-TYPE
    SYNTAX   INTEGER{disabled(0), enabled(1)}
    MAX-ACCESS  read-write
    STATUS   current
    DESCRIPTION "Enabled(1) or Disabled (0)"
    ::= {psAlarms1Masks 427}

a1DryContact13 OBJECT-TYPE
    SYNTAX   INTEGER{disabled(0), enabled(1)}
    MAX-ACCESS  read-write
    STATUS   current
    DESCRIPTION "Enabled(1) or Disabled (0)"
    ::= {psAlarms1Masks 428}

a1DryContact14 OBJECT-TYPE
    SYNTAX   INTEGER{disabled(0), enabled(1)}
    MAX-ACCESS  read-write
    STATUS   current
    DESCRIPTION "Enabled(1) or Disabled (0)"
    ::= {psAlarms1Masks 429}

a1DryContact15 OBJECT-TYPE
    SYNTAX   INTEGER{disabled(0), enabled(1)}
    MAX-ACCESS  read-write
    STATUS   current
    DESCRIPTION "Enabled(1) or Disabled (0)"
    ::= {psAlarms1Masks 430}

a1DryContact16 OBJECT-TYPE
    SYNTAX   INTEGER{disabled(0), enabled(1)}
    MAX-ACCESS  read-write
    STATUS   current
    DESCRIPTION "Enabled(1) or Disabled (0)"
    ::= {psAlarms1Masks 431}

---------------------------------------------------
a1BatteryLiIonAlarm OBJECT-TYPE  
    SYNTAX   INTEGER{disabled(0), enabled(1)}
    MAX-ACCESS  read-write
    STATUS   current
    DESCRIPTION "Enabled(1) or Disabled (0)"
    ::= {psAlarms1Masks 480}

--нет связи с BMS
a1BatteryBMSComFail OBJECT-TYPE  
    SYNTAX   INTEGER{disabled(0), enabled(1)}
    MAX-ACCESS  read-write
    STATUS   current
    DESCRIPTION "Enabled(1) or Disabled (0)"
    ::= {psAlarms1Masks 481}
--------------------------------------------------

--InternalErrors in psAlarms2Masks
a2InternallError OBJECT-TYPE
    SYNTAX   INTEGER{disabled(0), enabled(1)}
    MAX-ACCESS  read-write
    STATUS   current
    DESCRIPTION "Enabled(1) or Disabled (0)"
    ::= {psAlarms2Masks 1}

--OutputAlarms in psAlarms2Masks
a2LoadUnderVoltageAlarm OBJECT-TYPE
    SYNTAX   INTEGER{disabled(0), enabled(1)}
    MAX-ACCESS  read-write
    STATUS   current
    DESCRIPTION "Enabled(1) or Disabled (0)"
    ::= {psAlarms2Masks 32}

a2LoadOverVoltageAlarm OBJECT-TYPE
    SYNTAX   INTEGER{disabled(0), enabled(1)}
    MAX-ACCESS  read-write
    STATUS   current
    DESCRIPTION "Enabled(1) or Disabled (0)"
    ::= {psAlarms2Masks 33}

a2Termocompensation OBJECT-TYPE
    SYNTAX   INTEGER{disabled(0), enabled(1)}
    MAX-ACCESS  read-write
    STATUS   current
    DESCRIPTION "Enabled(1) or Disabled (0)"
    ::= {psAlarms2Masks 34}

--LoadFuses in psAlarms2Masks
a2LoadFuses1 OBJECT-TYPE
    SYNTAX   INTEGER{disabled(0), enabled(1)}
    MAX-ACCESS  read-write
    STATUS   current
    DESCRIPTION "Enabled(1) or Disabled (0)"
    ::= {psAlarms2Masks 35}

a2LoadFuses2 OBJECT-TYPE
    SYNTAX   INTEGER{disabled(0), enabled(1)}
    MAX-ACCESS  read-write
    STATUS   current
    DESCRIPTION "Enabled(1) or Disabled (0)"
    ::= {psAlarms2Masks 36}

a2LoadFuses3 OBJECT-TYPE
    SYNTAX   INTEGER{disabled(0), enabled(1)}
    MAX-ACCESS  read-write
    STATUS   current
    DESCRIPTION "Enabled(1) or Disabled (0)"
    ::= {psAlarms2Masks 37}

a2LoadFuses4 OBJECT-TYPE
    SYNTAX   INTEGER{disabled(0), enabled(1)}
    MAX-ACCESS  read-write
    STATUS   current
    DESCRIPTION "Enabled(1) or Disabled (0)"
    ::= {psAlarms2Masks 38}

a2LoadFuses5 OBJECT-TYPE
    SYNTAX   INTEGER{disabled(0), enabled(1)}
    MAX-ACCESS  read-write
    STATUS   current
    DESCRIPTION "Enabled(1) or Disabled (0)"
    ::= {psAlarms2Masks 39}

a2LoadFuses6 OBJECT-TYPE
    SYNTAX   INTEGER{disabled(0), enabled(1)}
    MAX-ACCESS  read-write
    STATUS   current
    DESCRIPTION "Enabled(1) or Disabled (0)"
    ::= {psAlarms2Masks 40}

a2LoadFuses7 OBJECT-TYPE
    SYNTAX   INTEGER{disabled(0), enabled(1)}
    MAX-ACCESS  read-write
    STATUS   current
    DESCRIPTION "Enabled(1) or Disabled (0)"
    ::= {psAlarms2Masks 41}

a2LoadFuses8 OBJECT-TYPE
    SYNTAX   INTEGER{disabled(0), enabled(1)}
    MAX-ACCESS  read-write
    STATUS   current
    DESCRIPTION "Enabled(1) or Disabled (0)"
    ::= {psAlarms2Masks 42}

a2LoadFuses9 OBJECT-TYPE
    SYNTAX   INTEGER{disabled(0), enabled(1)}
    MAX-ACCESS  read-write
    STATUS   current
    DESCRIPTION "Enabled(1) or Disabled (0)"
    ::= {psAlarms2Masks 43}

a2LoadFuses10 OBJECT-TYPE
    SYNTAX   INTEGER{disabled(0), enabled(1)}
    MAX-ACCESS  read-write
    STATUS   current
    DESCRIPTION "Enabled(1) or Disabled (0)"
    ::= {psAlarms2Masks 44}

a2LoadFuses11 OBJECT-TYPE
    SYNTAX   INTEGER{disabled(0), enabled(1)}
    MAX-ACCESS  read-write
    STATUS   current
    DESCRIPTION "Enabled(1) or Disabled (0)"
    ::= {psAlarms2Masks 45}

a2LoadFuses12 OBJECT-TYPE
    SYNTAX   INTEGER{disabled(0), enabled(1)}
    MAX-ACCESS  read-write
    STATUS   current
    DESCRIPTION "Enabled(1) or Disabled (0)"
    ::= {psAlarms2Masks 46}

a2LoadFuses13 OBJECT-TYPE
    SYNTAX   INTEGER{disabled(0), enabled(1)}
    MAX-ACCESS  read-write
    STATUS   current
    DESCRIPTION "Enabled(1) or Disabled (0)"
    ::= {psAlarms2Masks 47}

a2LoadFuses14 OBJECT-TYPE
    SYNTAX   INTEGER{disabled(0), enabled(1)}
    MAX-ACCESS  read-write
    STATUS   current
    DESCRIPTION "Enabled(1) or Disabled (0)"
    ::= {psAlarms2Masks 48}

a2LoadFuses15 OBJECT-TYPE
    SYNTAX   INTEGER{disabled(0), enabled(1)}
    MAX-ACCESS  read-write
    STATUS   current
    DESCRIPTION "Enabled(1) or Disabled (0)"
    ::= {psAlarms2Masks 49}

a2LoadFuses16 OBJECT-TYPE
    SYNTAX   INTEGER{disabled(0), enabled(1)}
    MAX-ACCESS  read-write
    STATUS   current
    DESCRIPTION "Enabled(1) or Disabled (0)"
    ::= {psAlarms2Masks 50}

a2LoadFuses17 OBJECT-TYPE
    SYNTAX   INTEGER{disabled(0), enabled(1)}
    MAX-ACCESS  read-write
    STATUS   current
    DESCRIPTION "Enabled(1) or Disabled (0)"
    ::= {psAlarms2Masks 51}

a2LoadFuses18 OBJECT-TYPE
    SYNTAX   INTEGER{disabled(0), enabled(1)}
    MAX-ACCESS  read-write
    STATUS   current
    DESCRIPTION "Enabled(1) or Disabled (0)"
    ::= {psAlarms2Masks 52}

a2LoadFuses19 OBJECT-TYPE
    SYNTAX   INTEGER{disabled(0), enabled(1)}
    MAX-ACCESS  read-write
    STATUS   current
    DESCRIPTION "Enabled(1) or Disabled (0)"
    ::= {psAlarms2Masks 53}

a2LoadFuses20 OBJECT-TYPE
    SYNTAX   INTEGER{disabled(0), enabled(1)}
    MAX-ACCESS  read-write
    STATUS   current
    DESCRIPTION "Enabled(1) or Disabled (0)"
    ::= {psAlarms2Masks 54}

a2LoadFuses21 OBJECT-TYPE
    SYNTAX   INTEGER{disabled(0), enabled(1)}
    MAX-ACCESS  read-write
    STATUS   current
    DESCRIPTION "Enabled(1) or Disabled (0)"
    ::= {psAlarms2Masks 55}

a2LoadFuses22 OBJECT-TYPE
    SYNTAX   INTEGER{disabled(0), enabled(1)}
    MAX-ACCESS  read-write
    STATUS   current
    DESCRIPTION "Enabled(1) or Disabled (0)"
    ::= {psAlarms2Masks 56}

a2LoadFuses23 OBJECT-TYPE
    SYNTAX   INTEGER{disabled(0), enabled(1)}
    MAX-ACCESS  read-write
    STATUS   current
    DESCRIPTION "Enabled(1) or Disabled (0)"
    ::= {psAlarms2Masks 57}

a2LoadFuses24 OBJECT-TYPE
    SYNTAX   INTEGER{disabled(0), enabled(1)}
    MAX-ACCESS  read-write
    STATUS   current
    DESCRIPTION "Enabled(1) or Disabled (0)"
    ::= {psAlarms2Masks 58}

a2LoadFuses25 OBJECT-TYPE
    SYNTAX   INTEGER{disabled(0), enabled(1)}
    MAX-ACCESS  read-write
    STATUS   current
    DESCRIPTION "Enabled(1) or Disabled (0)"
    ::= {psAlarms2Masks 59}

a2LoadFuses26 OBJECT-TYPE
    SYNTAX   INTEGER{disabled(0), enabled(1)}
    MAX-ACCESS  read-write
    STATUS   current
    DESCRIPTION "Enabled(1) or Disabled (0)"
    ::= {psAlarms2Masks 60}

a2LoadFuses27 OBJECT-TYPE
    SYNTAX   INTEGER{disabled(0), enabled(1)}
    MAX-ACCESS  read-write
    STATUS   current
    DESCRIPTION "Enabled(1) or Disabled (0)"
    ::= {psAlarms2Masks 61}

a2LoadFuses28 OBJECT-TYPE
    SYNTAX   INTEGER{disabled(0), enabled(1)}
    MAX-ACCESS  read-write
    STATUS   current
    DESCRIPTION "Enabled(1) or Disabled (0)"
    ::= {psAlarms2Masks 62}

a2LoadFuses29 OBJECT-TYPE
    SYNTAX   INTEGER{disabled(0), enabled(1)}
    MAX-ACCESS  read-write
    STATUS   current
    DESCRIPTION "Enabled(1) or Disabled (0)"
    ::= {psAlarms2Masks 63}

a2LoadFuses30 OBJECT-TYPE
    SYNTAX   INTEGER{disabled(0), enabled(1)}
    MAX-ACCESS  read-write
    STATUS   current
    DESCRIPTION "Enabled(1) or Disabled (0)"
    ::= {psAlarms2Masks 64}

a2LoadFuses31 OBJECT-TYPE
    SYNTAX   INTEGER{disabled(0), enabled(1)}
    MAX-ACCESS  read-write
    STATUS   current
    DESCRIPTION "Enabled(1) or Disabled (0)"
    ::= {psAlarms2Masks 65}

a2LoadFuses32 OBJECT-TYPE
    SYNTAX   INTEGER{disabled(0), enabled(1)}
    MAX-ACCESS  read-write
    STATUS   current
    DESCRIPTION "Enabled(1) or Disabled (0)"
    ::= {psAlarms2Masks 66}

a2LoadFuses33 OBJECT-TYPE
    SYNTAX   INTEGER{disabled(0), enabled(1)}
    MAX-ACCESS  read-write
    STATUS   current
    DESCRIPTION "Enabled(1) or Disabled (0)"
    ::= {psAlarms2Masks 67}

a2LoadFuses34 OBJECT-TYPE
    SYNTAX   INTEGER{disabled(0), enabled(1)}
    MAX-ACCESS  read-write
    STATUS   current
    DESCRIPTION "Enabled(1) or Disabled (0)"
    ::= {psAlarms2Masks 68}

a2LoadFuses35 OBJECT-TYPE
    SYNTAX   INTEGER{disabled(0), enabled(1)}
    MAX-ACCESS  read-write
    STATUS   current
    DESCRIPTION "Enabled(1) or Disabled (0)"
    ::= {psAlarms2Masks 69}

a2LoadFuses36 OBJECT-TYPE
    SYNTAX   INTEGER{disabled(0), enabled(1)}
    MAX-ACCESS  read-write
    STATUS   current
    DESCRIPTION "Enabled(1) or Disabled (0)"
    ::= {psAlarms2Masks 70}

a2LoadFuses37 OBJECT-TYPE
    SYNTAX   INTEGER{disabled(0), enabled(1)}
    MAX-ACCESS  read-write
    STATUS   current
    DESCRIPTION "Enabled(1) or Disabled (0)"
    ::= {psAlarms2Masks 71}

a2LoadFuses38 OBJECT-TYPE
    SYNTAX   INTEGER{disabled(0), enabled(1)}
    MAX-ACCESS  read-write
    STATUS   current
    DESCRIPTION "Enabled(1) or Disabled (0)"
    ::= {psAlarms2Masks 72}

a2LoadFuses39 OBJECT-TYPE
    SYNTAX   INTEGER{disabled(0), enabled(1)}
    MAX-ACCESS  read-write
    STATUS   current
    DESCRIPTION "Enabled(1) or Disabled (0)"
    ::= {psAlarms2Masks 73}

a2LoadFuses40 OBJECT-TYPE
    SYNTAX   INTEGER{disabled(0), enabled(1)}
    MAX-ACCESS  read-write
    STATUS   current
    DESCRIPTION "Enabled(1) or Disabled (0)"
    ::= {psAlarms2Masks 74}

a2LoadFuses41 OBJECT-TYPE
    SYNTAX   INTEGER{disabled(0), enabled(1)}
    MAX-ACCESS  read-write
    STATUS   current
    DESCRIPTION "Enabled(1) or Disabled (0)"
    ::= {psAlarms2Masks 75}

a2LoadFuses42 OBJECT-TYPE
    SYNTAX   INTEGER{disabled(0), enabled(1)}
    MAX-ACCESS  read-write
    STATUS   current
    DESCRIPTION "Enabled(1) or Disabled (0)"
    ::= {psAlarms2Masks 76}

a2LoadFuses43 OBJECT-TYPE
    SYNTAX   INTEGER{disabled(0), enabled(1)}
    MAX-ACCESS  read-write
    STATUS   current
    DESCRIPTION "Enabled(1) or Disabled (0)"
    ::= {psAlarms2Masks 77}

a2LoadFuses44 OBJECT-TYPE
    SYNTAX   INTEGER{disabled(0), enabled(1)}
    MAX-ACCESS  read-write
    STATUS   current
    DESCRIPTION "Enabled(1) or Disabled (0)"
    ::= {psAlarms2Masks 78}

a2LoadFuses45 OBJECT-TYPE
    SYNTAX   INTEGER{disabled(0), enabled(1)}
    MAX-ACCESS  read-write
    STATUS   current
    DESCRIPTION "Enabled(1) or Disabled (0)"
    ::= {psAlarms2Masks 79}

a2LoadFuses46 OBJECT-TYPE
    SYNTAX   INTEGER{disabled(0), enabled(1)}
    MAX-ACCESS  read-write
    STATUS   current
    DESCRIPTION "Enabled(1) or Disabled (0)"
    ::= {psAlarms2Masks 80}

a2LoadFuses47 OBJECT-TYPE
    SYNTAX   INTEGER{disabled(0), enabled(1)}
    MAX-ACCESS  read-write
    STATUS   current
    DESCRIPTION "Enabled(1) or Disabled (0)"
    ::= {psAlarms2Masks 81}

a2LoadFuses48 OBJECT-TYPE
    SYNTAX   INTEGER{disabled(0), enabled(1)}
    MAX-ACCESS  read-write
    STATUS   current
    DESCRIPTION "Enabled(1) or Disabled (0)"
    ::= {psAlarms2Masks 82}

a2LoadFuses49 OBJECT-TYPE
    SYNTAX   INTEGER{disabled(0), enabled(1)}
    MAX-ACCESS  read-write
    STATUS   current
    DESCRIPTION "Enabled(1) or Disabled (0)"
    ::= {psAlarms2Masks 83}

a2LoadFuses50 OBJECT-TYPE
    SYNTAX   INTEGER{disabled(0), enabled(1)}
    MAX-ACCESS  read-write
    STATUS   current
    DESCRIPTION "Enabled(1) or Disabled (0)"
    ::= {psAlarms2Masks 84}

a2LoadFuses51 OBJECT-TYPE
    SYNTAX   INTEGER{disabled(0), enabled(1)}
    MAX-ACCESS  read-write
    STATUS   current
    DESCRIPTION "Enabled(1) or Disabled (0)"
    ::= {psAlarms2Masks 85}

a2LoadFuses52 OBJECT-TYPE
    SYNTAX   INTEGER{disabled(0), enabled(1)}
    MAX-ACCESS  read-write
    STATUS   current
    DESCRIPTION "Enabled(1) or Disabled (0)"
    ::= {psAlarms2Masks 86}

a2UKDVAlarm OBJECT-TYPE
    SYNTAX   INTEGER{disabled(0), enabled(1)}
    MAX-ACCESS  read-write
    STATUS   current
    DESCRIPTION "Enabled(1) or Disabled (0)"
    ::= {psAlarms2Masks 87}

--Battery Events in psAlarms2Masks
a2BatteryDischarge OBJECT-TYPE
    SYNTAX   INTEGER{disabled(0), enabled(1)}
    MAX-ACCESS  read-write
    STATUS   current
    DESCRIPTION "Enabled(1) or Disabled (0)"
    ::= {psAlarms2Masks 96}

a2LowBatteryVoltage OBJECT-TYPE
    SYNTAX   INTEGER{disabled(0), enabled(1)}
    MAX-ACCESS  read-write
    STATUS   current
    DESCRIPTION "Enabled(1) or Disabled (0)"
    ::= {psAlarms2Masks 97}

a2BatteryCharge OBJECT-TYPE
    SYNTAX   INTEGER{disabled(0), enabled(1)}
    MAX-ACCESS  read-write
    STATUS   current
    DESCRIPTION "Enabled(1) or Disabled (0)"
    ::= {psAlarms2Masks 98}

a2BatteryBoost OBJECT-TYPE
    SYNTAX   INTEGER{disabled(0), enabled(1)}
    MAX-ACCESS  read-write
    STATUS   current
    DESCRIPTION "Enabled(1) or Disabled (0)"
    ::= {psAlarms2Masks 99}

a2BatteryFloat OBJECT-TYPE
    SYNTAX   INTEGER{disabled(0), enabled(1)}
    MAX-ACCESS  read-write
    STATUS   current
    DESCRIPTION "Enabled(1) or Disabled (0)"
    ::= {psAlarms2Masks 100}

a2BatteryEqualize OBJECT-TYPE
    SYNTAX   INTEGER{disabled(0), enabled(1)}
    MAX-ACCESS  read-write
    STATUS   current
    DESCRIPTION "Enabled(1) or Disabled (0)"
    ::= {psAlarms2Masks 101}

a2BatteryTest OBJECT-TYPE
    SYNTAX   INTEGER{disabled(0), enabled(1)}
    MAX-ACCESS  read-write
    STATUS   current
    DESCRIPTION "Enabled(1) or Disabled (0)"
    ::= {psAlarms2Masks 102}

a2BatteryFuse1Off OBJECT-TYPE
    SYNTAX   INTEGER{disabled(0), enabled(1)}
    MAX-ACCESS  read-write
    STATUS   current
    DESCRIPTION "Enabled(1) or Disabled (0)"
    ::= {psAlarms2Masks 103}

a2BatteryFuse2Off OBJECT-TYPE
    SYNTAX   INTEGER{disabled(0), enabled(1)}
    MAX-ACCESS  read-write
    STATUS   current
    DESCRIPTION "Enabled(1) or Disabled (0)"
    ::= {psAlarms2Masks 104}

a2BatteryFuse3Off OBJECT-TYPE
    SYNTAX   INTEGER{disabled(0), enabled(1)}
    MAX-ACCESS  read-write
    STATUS   current
    DESCRIPTION "Enabled(1) or Disabled (0)"
    ::= {psAlarms2Masks 105}

a2BatteryFuse4Off OBJECT-TYPE
    SYNTAX   INTEGER{disabled(0), enabled(1)}
    MAX-ACCESS  read-write
    STATUS   current
    DESCRIPTION "Enabled(1) or Disabled (0)"
    ::= {psAlarms2Masks 106}

---------------------------------------------------

a2BatteryBlockElGr1Alarm OBJECT-TYPE
    SYNTAX   INTEGER{disabled(0), enabled(1)}
    MAX-ACCESS  read-write
    STATUS   current
    DESCRIPTION "Enabled(1) or Disabled (0)"
    ::= {psAlarms2Masks 111}

a2BatteryBlockElGr2Alarm OBJECT-TYPE
    SYNTAX   INTEGER{disabled(0), enabled(1)}
    MAX-ACCESS  read-write
    STATUS   current
    DESCRIPTION "Enabled(1) or Disabled (0)"
    ::= {psAlarms2Masks 112}

a2BatteryBlockElGr3Alarm OBJECT-TYPE
    SYNTAX   INTEGER{disabled(0), enabled(1)}
    MAX-ACCESS  read-write
    STATUS   current
    DESCRIPTION "Enabled(1) or Disabled (0)"
    ::= {psAlarms2Masks 113}

a2BatteryBlockElGr4Alarm OBJECT-TYPE
    SYNTAX   INTEGER{disabled(0), enabled(1)}
    MAX-ACCESS  read-write
    STATUS   current
    DESCRIPTION "Enabled(1) or Disabled (0)"
    ::= {psAlarms2Masks 114}
----------------------------------------------------

a2UPKBAlarm OBJECT-TYPE
    SYNTAX   INTEGER{disabled(0), enabled(1)}
    MAX-ACCESS  read-write
    STATUS   current
    DESCRIPTION "Enabled(1) or Disabled (0)"
    ::= {psAlarms2Masks 119}

a2ChargeCurrentLess1A OBJECT-TYPE
    SYNTAX   INTEGER{disabled(0), enabled(1)}
    MAX-ACCESS  read-write
    STATUS   current
    DESCRIPTION "Enabled(1) or Disabled (0)"
    ::= {psAlarms2Masks 120}

a2ChargeCurrentLess2A OBJECT-TYPE
    SYNTAX   INTEGER{disabled(0), enabled(1)}
    MAX-ACCESS  read-write
    STATUS   current
    DESCRIPTION "Enabled(1) or Disabled (0)"
    ::= {psAlarms2Masks 121}

a2ChargeCurrentLess3A OBJECT-TYPE
    SYNTAX   INTEGER{disabled(0), enabled(1)}
    MAX-ACCESS  read-write
    STATUS   current
    DESCRIPTION "Enabled(1) or Disabled (0)"
    ::= {psAlarms2Masks 122}

a2ChargeCurrentLess4A OBJECT-TYPE
    SYNTAX   INTEGER{disabled(0), enabled(1)}
    MAX-ACCESS  read-write
    STATUS   current
    DESCRIPTION "Enabled(1) or Disabled (0)"
    ::= {psAlarms2Masks 123}

a2ChargeCurrentLess5A OBJECT-TYPE
    SYNTAX   INTEGER{disabled(0), enabled(1)}
    MAX-ACCESS  read-write
    STATUS   current
    DESCRIPTION "Enabled(1) or Disabled (0)"
    ::= {psAlarms2Masks 124}

a2BatteryOverheat OBJECT-TYPE
    SYNTAX   INTEGER{disabled(0), enabled(1)}
    MAX-ACCESS  read-write
    STATUS   current
    DESCRIPTION "Enabled(1) or Disabled (0)"
    ::= {psAlarms2Masks 125}

-------------------------------------------------------------------------------------------
-------------------------------------------------------------------------------------------
a2BatteryShortTest OBJECT-TYPE
    SYNTAX   INTEGER{disabled(0), enabled(1)}
    MAX-ACCESS  read-write
    STATUS   current
    DESCRIPTION "Enabled(1) or Disabled (0)"
    ::= {psAlarms2Masks 126}

a2BatteryShortTestFail OBJECT-TYPE  
    SYNTAX   INTEGER{disabled(0), enabled(1)}
    MAX-ACCESS  read-write
    STATUS   current
    DESCRIPTION "Enabled(1) or Disabled (0)"
    ::= {psAlarms2Masks 127}

-------------------------------------------------------------------------------------------
-------------------------------------------------------------------------------------------    

a2BLVDoff OBJECT-TYPE
    SYNTAX   INTEGER{disabled(0), enabled(1)}
    MAX-ACCESS  read-write
    STATUS   current
    DESCRIPTION "Enabled(1) or Disabled (0)"
    ::= {psAlarms2Masks 128}

a2LLVD1off OBJECT-TYPE
    SYNTAX   INTEGER{disabled(0), enabled(1)}
    MAX-ACCESS  read-write
    STATUS   current
    DESCRIPTION "Enabled(1) or Disabled (0)"
    ::= {psAlarms2Masks 129}

a2LLVD2off OBJECT-TYPE
    SYNTAX   INTEGER{disabled(0), enabled(1)}
    MAX-ACCESS  read-write
    STATUS   current
    DESCRIPTION "Enabled(1) or Disabled (0)"
    ::= {psAlarms2Masks 130}

--VBVAlarm in psAlarms2Masks
a2VBV1Alarm OBJECT-TYPE
    SYNTAX   INTEGER{disabled(0), enabled(1)}
    MAX-ACCESS  read-write
    STATUS   current
    DESCRIPTION "Alarm of rectifier1 Enabled(1) or Disabled (0)"
    ::= {psAlarms2Masks 160}

a2VBV2Alarm OBJECT-TYPE
    SYNTAX   INTEGER{disabled(0), enabled(1)}
    MAX-ACCESS  read-write
    STATUS   current
    DESCRIPTION "Alarm of rectifier2 Enabled(1) or Disabled (0)"
    ::= {psAlarms2Masks 161}

a2VBV3Alarm OBJECT-TYPE
    SYNTAX   INTEGER{disabled(0), enabled(1)}
    MAX-ACCESS  read-write
    STATUS   current
    DESCRIPTION "Alarm of rectifier3 Enabled(1) or Disabled (0)"
    ::= {psAlarms2Masks 162}

a2VBV4Alarm OBJECT-TYPE
    SYNTAX   INTEGER{disabled(0), enabled(1)}
    MAX-ACCESS  read-write
    STATUS   current
    DESCRIPTION "Alarm of rectifier4 Enabled(1) or Disabled (0)"
    ::= {psAlarms2Masks 163}

a2VBV5Alarm OBJECT-TYPE
    SYNTAX   INTEGER{disabled(0), enabled(1)}
    MAX-ACCESS  read-write
    STATUS   current
    DESCRIPTION "Alarm of rectifier5 Enabled(1) or Disabled (0)"
    ::= {psAlarms2Masks 164}

a2VBV6Alarm OBJECT-TYPE
    SYNTAX   INTEGER{disabled(0), enabled(1)}
    MAX-ACCESS  read-write
    STATUS   current
    DESCRIPTION "Alarm of rectifier6 Enabled(1) or Disabled (0)"
    ::= {psAlarms2Masks 165}

a2VBV7Alarm OBJECT-TYPE
    SYNTAX   INTEGER{disabled(0), enabled(1)}
    MAX-ACCESS  read-write
    STATUS   current
    DESCRIPTION "Alarm of rectifier7 Enabled(1) or Disabled (0)"
    ::= {psAlarms2Masks 166}

a2VBV8Alarm OBJECT-TYPE
    SYNTAX   INTEGER{disabled(0), enabled(1)}
    MAX-ACCESS  read-write
    STATUS   current
    DESCRIPTION "Alarm of rectifier8 Enabled(1) or Disabled (0)"
    ::= {psAlarms2Masks 167}

a2VBV9Alarm OBJECT-TYPE
    SYNTAX   INTEGER{disabled(0), enabled(1)}
    MAX-ACCESS  read-write
    STATUS   current
    DESCRIPTION "Alarm of rectifier9 Enabled(1) or Disabled (0)"
    ::= {psAlarms2Masks 168}

a2VBV10Alarm OBJECT-TYPE
    SYNTAX   INTEGER{disabled(0), enabled(1)}
    MAX-ACCESS  read-write
    STATUS   current
    DESCRIPTION "Alarm of rectifier10 Enabled(1) or Disabled (0)"
    ::= {psAlarms2Masks 169}

a2VBV11Alarm OBJECT-TYPE
    SYNTAX   INTEGER{disabled(0), enabled(1)}
    MAX-ACCESS  read-write
    STATUS   current
    DESCRIPTION "Alarm of rectifier11 Enabled(1) or Disabled (0)"
    ::= {psAlarms2Masks 170}

a2VBV12Alarm OBJECT-TYPE
    SYNTAX   INTEGER{disabled(0), enabled(1)}
    MAX-ACCESS  read-write
    STATUS   current
    DESCRIPTION "Alarm of rectifier12 Enabled(1) or Disabled (0)"
    ::= {psAlarms2Masks 171}

a2VBV13Alarm OBJECT-TYPE
    SYNTAX   INTEGER{disabled(0), enabled(1)}
    MAX-ACCESS  read-write
    STATUS   current
    DESCRIPTION "Alarm of rectifier13 Enabled(1) or Disabled (0)"
    ::= {psAlarms2Masks 172}

a2VBV14Alarm OBJECT-TYPE
    SYNTAX   INTEGER{disabled(0), enabled(1)}
    MAX-ACCESS  read-write
    STATUS   current
    DESCRIPTION "Alarm of rectifier14 Enabled(1) or Disabled (0)"
    ::= {psAlarms2Masks 173}

a2VBV15Alarm OBJECT-TYPE
    SYNTAX   INTEGER{disabled(0), enabled(1)}
    MAX-ACCESS  read-write
    STATUS   current
    DESCRIPTION "Alarm of rectifier15 Enabled(1) or Disabled (0)"
    ::= {psAlarms2Masks 174}

a2VBV16Alarm OBJECT-TYPE
    SYNTAX   INTEGER{disabled(0), enabled(1)}
    MAX-ACCESS  read-write
    STATUS   current
    DESCRIPTION "Alarm of rectifier16 Enabled(1) or Disabled (0)"
    ::= {psAlarms2Masks 175}

a2VBV17Alarm OBJECT-TYPE
    SYNTAX   INTEGER{disabled(0), enabled(1)}
    MAX-ACCESS  read-write
    STATUS   current
    DESCRIPTION "Alarm of rectifier17 Enabled(1) or Disabled (0)"
    ::= {psAlarms2Masks 176}

a2VBV18Alarm OBJECT-TYPE
    SYNTAX   INTEGER{disabled(0), enabled(1)}
    MAX-ACCESS  read-write
    STATUS   current
    DESCRIPTION "Alarm of rectifier18 Enabled(1) or Disabled (0)"
    ::= {psAlarms2Masks 177}

a2VBV19Alarm OBJECT-TYPE
    SYNTAX   INTEGER{disabled(0), enabled(1)}
    MAX-ACCESS  read-write
    STATUS   current
    DESCRIPTION "Alarm of rectifier19 Enabled(1) or Disabled (0)"
    ::= {psAlarms2Masks 178}

a2VBV20Alarm OBJECT-TYPE
    SYNTAX   INTEGER{disabled(0), enabled(1)}
    MAX-ACCESS  read-write
    STATUS   current
    DESCRIPTION "Alarm of rectifier20 Enabled(1) or Disabled (0)"
    ::= {psAlarms2Masks 179}

a2VBV21Alarm OBJECT-TYPE
    SYNTAX   INTEGER{disabled(0), enabled(1)}
    MAX-ACCESS  read-write
    STATUS   current
    DESCRIPTION "Alarm of rectifier21 Enabled(1) or Disabled (0)"
    ::= {psAlarms2Masks 180}

a2VBV22Alarm OBJECT-TYPE
    SYNTAX   INTEGER{disabled(0), enabled(1)}
    MAX-ACCESS  read-write
    STATUS   current
    DESCRIPTION "Alarm of rectifier22 Enabled(1) or Disabled (0)"
    ::= {psAlarms2Masks 181}

a2VBV23Alarm OBJECT-TYPE
    SYNTAX   INTEGER{disabled(0), enabled(1)}
    MAX-ACCESS  read-write
    STATUS   current
    DESCRIPTION "Alarm of rectifier23 Enabled(1) or Disabled (0)"
    ::= {psAlarms2Masks 182}

a2VBV24Alarm OBJECT-TYPE
    SYNTAX   INTEGER{disabled(0), enabled(1)}
    MAX-ACCESS  read-write
    STATUS   current
    DESCRIPTION "Alarm of rectifier24 Enabled(1) or Disabled (0)"
    ::= {psAlarms2Masks 183}

a2VBV25Alarm OBJECT-TYPE
    SYNTAX   INTEGER{disabled(0), enabled(1)}
    MAX-ACCESS  read-write
    STATUS   current
    DESCRIPTION "Alarm of rectifier25 Enabled(1) or Disabled (0)"
    ::= {psAlarms2Masks 184}

a2VBV26Alarm OBJECT-TYPE
    SYNTAX   INTEGER{disabled(0), enabled(1)}
    MAX-ACCESS  read-write
    STATUS   current
    DESCRIPTION "Alarm of rectifier26 Enabled(1) or Disabled (0)"
    ::= {psAlarms2Masks 185}

a2VBV27Alarm OBJECT-TYPE
    SYNTAX   INTEGER{disabled(0), enabled(1)}
    MAX-ACCESS  read-write
    STATUS   current
    DESCRIPTION "Alarm of rectifier27 Enabled(1) or Disabled (0)"
    ::= {psAlarms2Masks 186}

a2VBV28Alarm OBJECT-TYPE
    SYNTAX   INTEGER{disabled(0), enabled(1)}
    MAX-ACCESS  read-write
    STATUS   current
    DESCRIPTION "Alarm of rectifier28 Enabled(1) or Disabled (0)"
    ::= {psAlarms2Masks 187}

a2VBV29Alarm OBJECT-TYPE
    SYNTAX   INTEGER{disabled(0), enabled(1)}
    MAX-ACCESS  read-write
    STATUS   current
    DESCRIPTION "Alarm of rectifier29 Enabled(1) or Disabled (0)"
    ::= {psAlarms2Masks 188}

a2VBV30Alarm OBJECT-TYPE
    SYNTAX   INTEGER{disabled(0), enabled(1)}
    MAX-ACCESS  read-write
    STATUS   current
    DESCRIPTION "Alarm of rectifier30 Enabled(1) or Disabled (0)"
    ::= {psAlarms2Masks 189}

a2VBV31Alarm OBJECT-TYPE
    SYNTAX   INTEGER{disabled(0), enabled(1)}
    MAX-ACCESS  read-write
    STATUS   current
    DESCRIPTION "Alarm of rectifier31 Enabled(1) or Disabled (0)"
    ::= {psAlarms2Masks 190}

a2VBV32Alarm OBJECT-TYPE
    SYNTAX   INTEGER{disabled(0), enabled(1)}
    MAX-ACCESS  read-write
    STATUS   current
    DESCRIPTION "Alarm of rectifier32 Enabled(1) or Disabled (0)"
    ::= {psAlarms2Masks 191}

a2VBV33Alarm OBJECT-TYPE
    SYNTAX   INTEGER{disabled(0), enabled(1)}
    MAX-ACCESS  read-write
    STATUS   current
    DESCRIPTION "Alarm of rectifier33 Enabled(1) or Disabled (0)"
    ::= {psAlarms2Masks 192}

a2VBV34Alarm OBJECT-TYPE
    SYNTAX   INTEGER{disabled(0), enabled(1)}
    MAX-ACCESS  read-write
    STATUS   current
    DESCRIPTION "Alarm of rectifier34 Enabled(1) or Disabled (0)"
    ::= {psAlarms2Masks 193}

a2VBV35Alarm OBJECT-TYPE
    SYNTAX   INTEGER{disabled(0), enabled(1)}
    MAX-ACCESS  read-write
    STATUS   current
    DESCRIPTION "Alarm of rectifier35 Enabled(1) or Disabled (0)"
    ::= {psAlarms2Masks 194}

a2VBV36Alarm OBJECT-TYPE
    SYNTAX   INTEGER{disabled(0), enabled(1)}
    MAX-ACCESS  read-write
    STATUS   current
    DESCRIPTION "Alarm of rectifier36 Enabled(1) or Disabled (0)"
    ::= {psAlarms2Masks 195}

a2VBV37Alarm OBJECT-TYPE
    SYNTAX   INTEGER{disabled(0), enabled(1)}
    MAX-ACCESS  read-write
    STATUS   current
    DESCRIPTION "Alarm of rectifier37 Enabled(1) or Disabled (0)"
    ::= {psAlarms2Masks 196}

a2VBV38Alarm OBJECT-TYPE
    SYNTAX   INTEGER{disabled(0), enabled(1)}
    MAX-ACCESS  read-write
    STATUS   current
    DESCRIPTION "Alarm of rectifier38 Enabled(1) or Disabled (0)"
    ::= {psAlarms2Masks 197}

a2VBV39Alarm OBJECT-TYPE
    SYNTAX   INTEGER{disabled(0), enabled(1)}
    MAX-ACCESS  read-write
    STATUS   current
    DESCRIPTION "Alarm of rectifier39 Enabled(1) or Disabled (0)"
    ::= {psAlarms2Masks 198}

a2VBV40Alarm OBJECT-TYPE
    SYNTAX   INTEGER{disabled(0), enabled(1)}
    MAX-ACCESS  read-write
    STATUS   current
    DESCRIPTION "Alarm of rectifier40 Enabled(1) or Disabled (0)"
    ::= {psAlarms2Masks 199}

a2VBV41Alarm OBJECT-TYPE
    SYNTAX   INTEGER{disabled(0), enabled(1)}
    MAX-ACCESS  read-write
    STATUS   current
    DESCRIPTION "Alarm of rectifier41 Enabled(1) or Disabled (0)"
    ::= {psAlarms2Masks 200}

a2VBV42Alarm OBJECT-TYPE
    SYNTAX   INTEGER{disabled(0), enabled(1)}
    MAX-ACCESS  read-write
    STATUS   current
    DESCRIPTION "Alarm of rectifier42 Enabled(1) or Disabled (0)"
    ::= {psAlarms2Masks 201}

a2VBV43Alarm OBJECT-TYPE
    SYNTAX   INTEGER{disabled(0), enabled(1)}
    MAX-ACCESS  read-write
    STATUS   current
    DESCRIPTION "Alarm of rectifier43 Enabled(1) or Disabled (0)"
    ::= {psAlarms2Masks 202}

a2VBV44Alarm OBJECT-TYPE
    SYNTAX   INTEGER{disabled(0), enabled(1)}
    MAX-ACCESS  read-write
    STATUS   current
    DESCRIPTION "Alarm of rectifier44 Enabled(1) or Disabled (0)"
    ::= {psAlarms2Masks 203}

a2VBV45Alarm OBJECT-TYPE
    SYNTAX   INTEGER{disabled(0), enabled(1)}
    MAX-ACCESS  read-write
    STATUS   current
    DESCRIPTION "Alarm of rectifier45 Enabled(1) or Disabled (0)"
    ::= {psAlarms2Masks 204}

a2VBV46Alarm OBJECT-TYPE
    SYNTAX   INTEGER{disabled(0), enabled(1)}
    MAX-ACCESS  read-write
    STATUS   current
    DESCRIPTION "Alarm of rectifier46 Enabled(1) or Disabled (0)"
    ::= {psAlarms2Masks 205}

a2VBV47Alarm OBJECT-TYPE
    SYNTAX   INTEGER{disabled(0), enabled(1)}
    MAX-ACCESS  read-write
    STATUS   current
    DESCRIPTION "Alarm of rectifier47 Enabled(1) or Disabled (0)"
    ::= {psAlarms2Masks 206}

a2VBV48Alarm OBJECT-TYPE
    SYNTAX   INTEGER{disabled(0), enabled(1)}
    MAX-ACCESS  read-write
    STATUS   current
    DESCRIPTION "Alarm of rectifier48 Enabled(1) or Disabled (0)"
    ::= {psAlarms2Masks 207}

a2VBV49Alarm OBJECT-TYPE
    SYNTAX   INTEGER{disabled(0), enabled(1)}
    MAX-ACCESS  read-write
    STATUS   current
    DESCRIPTION "Alarm of rectifier49 Enabled(1) or Disabled (0)"
    ::= {psAlarms2Masks 208}

a2VBV50Alarm OBJECT-TYPE
    SYNTAX   INTEGER{disabled(0), enabled(1)}
    MAX-ACCESS  read-write
    STATUS   current
    DESCRIPTION "Alarm of rectifier50 Enabled(1) or Disabled (0)"
    ::= {psAlarms2Masks 209}

a2VBV51Alarm OBJECT-TYPE
    SYNTAX   INTEGER{disabled(0), enabled(1)}
    MAX-ACCESS  read-write
    STATUS   current
    DESCRIPTION "Alarm of rectifier51 Enabled(1) or Disabled (0)"
    ::= {psAlarms2Masks 210}

a2VBV52Alarm OBJECT-TYPE
    SYNTAX   INTEGER{disabled(0), enabled(1)}
    MAX-ACCESS  read-write
    STATUS   current
    DESCRIPTION "Alarm of rectifier52 Enabled(1) or Disabled (0)"
    ::= {psAlarms2Masks 211}

a2VBV53Alarm OBJECT-TYPE
    SYNTAX   INTEGER{disabled(0), enabled(1)}
    MAX-ACCESS  read-write
    STATUS   current
    DESCRIPTION "Alarm of rectifier53 Enabled(1) or Disabled (0)"
    ::= {psAlarms2Masks 212}

a2VBV54Alarm OBJECT-TYPE
    SYNTAX   INTEGER{disabled(0), enabled(1)}
    MAX-ACCESS  read-write
    STATUS   current
    DESCRIPTION "Alarm of rectifier54 Enabled(1) or Disabled (0)"
    ::= {psAlarms2Masks 213}

a2VBV55Alarm OBJECT-TYPE
    SYNTAX   INTEGER{disabled(0), enabled(1)}
    MAX-ACCESS  read-write
    STATUS   current
    DESCRIPTION "Alarm of rectifier55 Enabled(1) or Disabled (0)"
    ::= {psAlarms2Masks 214}

a2VBV56Alarm OBJECT-TYPE
    SYNTAX   INTEGER{disabled(0), enabled(1)}
    MAX-ACCESS  read-write
    STATUS   current
    DESCRIPTION "Alarm of rectifier56 Enabled(1) or Disabled (0)"
    ::= {psAlarms2Masks 215}

a2VBV57Alarm OBJECT-TYPE
    SYNTAX   INTEGER{disabled(0), enabled(1)}
    MAX-ACCESS  read-write
    STATUS   current
    DESCRIPTION "Alarm of rectifier57 Enabled(1) or Disabled (0)"
    ::= {psAlarms2Masks 216}

a2VBV58Alarm OBJECT-TYPE
    SYNTAX   INTEGER{disabled(0), enabled(1)}
    MAX-ACCESS  read-write
    STATUS   current
    DESCRIPTION "Alarm of rectifier58 Enabled(1) or Disabled (0)"
    ::= {psAlarms2Masks 217}

a2VBV59Alarm OBJECT-TYPE
    SYNTAX   INTEGER{disabled(0), enabled(1)}
    MAX-ACCESS  read-write
    STATUS   current
    DESCRIPTION "Alarm of rectifier59 Enabled(1) or Disabled (0)"
    ::= {psAlarms2Masks 218}

a2VBV60Alarm OBJECT-TYPE
    SYNTAX   INTEGER{disabled(0), enabled(1)}
    MAX-ACCESS  read-write
    STATUS   current
    DESCRIPTION "Alarm of rectifier60 Enabled(1) or Disabled (0)"
    ::= {psAlarms2Masks 219}

a2VBV61Alarm OBJECT-TYPE
    SYNTAX   INTEGER{disabled(0), enabled(1)}
    MAX-ACCESS  read-write
    STATUS   current
    DESCRIPTION "Alarm of rectifier61 Enabled(1) or Disabled (0)"
    ::= {psAlarms2Masks 220}

a2VBV62Alarm OBJECT-TYPE
    SYNTAX   INTEGER{disabled(0), enabled(1)}
    MAX-ACCESS  read-write
    STATUS   current
    DESCRIPTION "Alarm of rectifier62 Enabled(1) or Disabled (0)"
    ::= {psAlarms2Masks 221}

a2VBV63Alarm OBJECT-TYPE
    SYNTAX   INTEGER{disabled(0), enabled(1)}
    MAX-ACCESS  read-write
    STATUS   current
    DESCRIPTION "Alarm of rectifier63 Enabled(1) or Disabled (0)"
    ::= {psAlarms2Masks 222}

a2VBV64Alarm OBJECT-TYPE
    SYNTAX   INTEGER{disabled(0), enabled(1)}
    MAX-ACCESS  read-write
    STATUS   current
    DESCRIPTION "Alarm of rectifier64 Enabled(1) or Disabled (0)"
    ::= {psAlarms2Masks 223}

a2VBV65Alarm OBJECT-TYPE
    SYNTAX   INTEGER{disabled(0), enabled(1)}
    MAX-ACCESS  read-write
    STATUS   current
    DESCRIPTION "Alarm of rectifier65 Enabled(1) or Disabled (0)"
    ::= {psAlarms2Masks 224}

a2VBV66Alarm OBJECT-TYPE
    SYNTAX   INTEGER{disabled(0), enabled(1)}
    MAX-ACCESS  read-write
    STATUS   current
    DESCRIPTION "Alarm of rectifier66 Enabled(1) or Disabled (0)"
    ::= {psAlarms2Masks 225}

a2VBV67Alarm OBJECT-TYPE
    SYNTAX   INTEGER{disabled(0), enabled(1)}
    MAX-ACCESS  read-write
    STATUS   current
    DESCRIPTION "Alarm of rectifier67 Enabled(1) or Disabled (0)"
    ::= {psAlarms2Masks 226}

a2VBV68Alarm OBJECT-TYPE
    SYNTAX   INTEGER{disabled(0), enabled(1)}
    MAX-ACCESS  read-write
    STATUS   current
    DESCRIPTION "Alarm of rectifier68 Enabled(1) or Disabled (0)"
    ::= {psAlarms2Masks 227}

a2VBV69Alarm OBJECT-TYPE
    SYNTAX   INTEGER{disabled(0), enabled(1)}
    MAX-ACCESS  read-write
    STATUS   current
    DESCRIPTION "Alarm of rectifier69 Enabled(1) or Disabled (0)"
    ::= {psAlarms2Masks 228}

a2VBV70Alarm OBJECT-TYPE
    SYNTAX   INTEGER{disabled(0), enabled(1)}
    MAX-ACCESS  read-write
    STATUS   current
    DESCRIPTION "Alarm of rectifier70 Enabled(1) or Disabled (0)"
    ::= {psAlarms2Masks 229}

a2VBV71Alarm OBJECT-TYPE
    SYNTAX   INTEGER{disabled(0), enabled(1)}
    MAX-ACCESS  read-write
    STATUS   current
    DESCRIPTION "Alarm of rectifier71 Enabled(1) or Disabled (0)"
    ::= {psAlarms2Masks 230}

a2VBV72Alarm OBJECT-TYPE
    SYNTAX   INTEGER{disabled(0), enabled(1)}
    MAX-ACCESS  read-write
    STATUS   current
    DESCRIPTION "Alarm of rectifier72 Enabled(1) or Disabled (0)"
    ::= {psAlarms2Masks 231}

a2VBV73Alarm OBJECT-TYPE
    SYNTAX   INTEGER{disabled(0), enabled(1)}
    MAX-ACCESS  read-write
    STATUS   current
    DESCRIPTION "Alarm of rectifier73 Enabled(1) or Disabled (0)"
    ::= {psAlarms2Masks 232}

a2VBV74Alarm OBJECT-TYPE
    SYNTAX   INTEGER{disabled(0), enabled(1)}
    MAX-ACCESS  read-write
    STATUS   current
    DESCRIPTION "Alarm of rectifier74 Enabled(1) or Disabled (0)"
    ::= {psAlarms2Masks 233}

a2VBV75Alarm OBJECT-TYPE
    SYNTAX   INTEGER{disabled(0), enabled(1)}
    MAX-ACCESS  read-write
    STATUS   current
    DESCRIPTION "Alarm of rectifier75 Enabled(1) or Disabled (0)"
    ::= {psAlarms2Masks 234}

a2VBV76Alarm OBJECT-TYPE
    SYNTAX   INTEGER{disabled(0), enabled(1)}
    MAX-ACCESS  read-write
    STATUS   current
    DESCRIPTION "Alarm of rectifier76 Enabled(1) or Disabled (0)"
    ::= {psAlarms2Masks 235}

a2VBV77Alarm OBJECT-TYPE
    SYNTAX   INTEGER{disabled(0), enabled(1)}
    MAX-ACCESS  read-write
    STATUS   current
    DESCRIPTION "Alarm of rectifier77 Enabled(1) or Disabled (0)"
    ::= {psAlarms2Masks 236}

a2VBV78Alarm OBJECT-TYPE
    SYNTAX   INTEGER{disabled(0), enabled(1)}
    MAX-ACCESS  read-write
    STATUS   current
    DESCRIPTION "Alarm of rectifier78 Enabled(1) or Disabled (0)"
    ::= {psAlarms2Masks 237}

a2VBV79Alarm OBJECT-TYPE
    SYNTAX   INTEGER{disabled(0), enabled(1)}
    MAX-ACCESS  read-write
    STATUS   current
    DESCRIPTION "Alarm of rectifier79 Enabled(1) or Disabled (0)"
    ::= {psAlarms2Masks 238}

a2VBV80Alarm OBJECT-TYPE
    SYNTAX   INTEGER{disabled(0), enabled(1)}
    MAX-ACCESS  read-write
    STATUS   current
    DESCRIPTION "Alarm of rectifier80 Enabled(1) or Disabled (0)"
    ::= {psAlarms2Masks 239}

a2VBV81Alarm OBJECT-TYPE
    SYNTAX   INTEGER{disabled(0), enabled(1)}
    MAX-ACCESS  read-write
    STATUS   current
    DESCRIPTION "Alarm of rectifier81 Enabled(1) or Disabled (0)"
    ::= {psAlarms2Masks 240}

a2VBV82Alarm OBJECT-TYPE
    SYNTAX   INTEGER{disabled(0), enabled(1)}
    MAX-ACCESS  read-write
    STATUS   current
    DESCRIPTION "Alarm of rectifier82 Enabled(1) or Disabled (0)"
    ::= {psAlarms2Masks 241}

a2VBV83Alarm OBJECT-TYPE
    SYNTAX   INTEGER{disabled(0), enabled(1)}
    MAX-ACCESS  read-write
    STATUS   current
    DESCRIPTION "Alarm of rectifier83 Enabled(1) or Disabled (0)"
    ::= {psAlarms2Masks 242}

a2VBV84Alarm OBJECT-TYPE
    SYNTAX   INTEGER{disabled(0), enabled(1)}
    MAX-ACCESS  read-write
    STATUS   current
    DESCRIPTION "Alarm of rectifier84 Enabled(1) or Disabled (0)"
    ::= {psAlarms2Masks 243}

a2VBV85Alarm OBJECT-TYPE
    SYNTAX   INTEGER{disabled(0), enabled(1)}
    MAX-ACCESS  read-write
    STATUS   current
    DESCRIPTION "Alarm of rectifier85 Enabled(1) or Disabled (0)"
    ::= {psAlarms2Masks 244}

a2VBV86Alarm OBJECT-TYPE
    SYNTAX   INTEGER{disabled(0), enabled(1)}
    MAX-ACCESS  read-write
    STATUS   current
    DESCRIPTION "Alarm of rectifier86 Enabled(1) or Disabled (0)"
    ::= {psAlarms2Masks 245}

a2VBV87Alarm OBJECT-TYPE
    SYNTAX   INTEGER{disabled(0), enabled(1)}
    MAX-ACCESS  read-write
    STATUS   current
    DESCRIPTION "Alarm of rectifier87 Enabled(1) or Disabled (0)"
    ::= {psAlarms2Masks 246}

a2VBV88Alarm OBJECT-TYPE
    SYNTAX   INTEGER{disabled(0), enabled(1)}
    MAX-ACCESS  read-write
    STATUS   current
    DESCRIPTION "Alarm of rectifier88 Enabled(1) or Disabled (0)"
    ::= {psAlarms2Masks 247}

a2VBV89Alarm OBJECT-TYPE
    SYNTAX   INTEGER{disabled(0), enabled(1)}
    MAX-ACCESS  read-write
    STATUS   current
    DESCRIPTION "Alarm of rectifier89 Enabled(1) or Disabled (0)"
    ::= {psAlarms2Masks 248}

a2VBV90Alarm OBJECT-TYPE
    SYNTAX   INTEGER{disabled(0), enabled(1)}
    MAX-ACCESS  read-write
    STATUS   current
    DESCRIPTION "Alarm of rectifier90 Enabled(1) or Disabled (0)"
    ::= {psAlarms2Masks 249}

a2VBV91Alarm OBJECT-TYPE
    SYNTAX   INTEGER{disabled(0), enabled(1)}
    MAX-ACCESS  read-write
    STATUS   current
    DESCRIPTION "Alarm of rectifier91 Enabled(1) or Disabled (0)"
    ::= {psAlarms2Masks 250}

a2VBV92Alarm OBJECT-TYPE
    SYNTAX   INTEGER{disabled(0), enabled(1)}
    MAX-ACCESS  read-write
    STATUS   current
    DESCRIPTION "Alarm of rectifier92 Enabled(1) or Disabled (0)"
    ::= {psAlarms2Masks 251}

a2VBV93Alarm OBJECT-TYPE
    SYNTAX   INTEGER{disabled(0), enabled(1)}
    MAX-ACCESS  read-write
    STATUS   current
    DESCRIPTION "Alarm of rectifier93 Enabled(1) or Disabled (0)"
    ::= {psAlarms2Masks 252}

a2VBV94Alarm OBJECT-TYPE
    SYNTAX   INTEGER{disabled(0), enabled(1)}
    MAX-ACCESS  read-write
    STATUS   current
    DESCRIPTION "Alarm of rectifier94 Enabled(1) or Disabled (0)"
    ::= {psAlarms2Masks 253}

a2VBV95Alarm OBJECT-TYPE
    SYNTAX   INTEGER{disabled(0), enabled(1)}
    MAX-ACCESS  read-write
    STATUS   current
    DESCRIPTION "Alarm of rectifier95 Enabled(1) or Disabled (0)"
    ::= {psAlarms2Masks 254}

a2VBV96Alarm OBJECT-TYPE
    SYNTAX   INTEGER{disabled(0), enabled(1)}
    MAX-ACCESS  read-write
    STATUS   current
    DESCRIPTION "Alarm of rectifier96 Enabled(1) or Disabled (0)"
    ::= {psAlarms2Masks 255}

a2VBV97Alarm OBJECT-TYPE
    SYNTAX   INTEGER{disabled(0), enabled(1)}
    MAX-ACCESS  read-write
    STATUS   current
    DESCRIPTION "Alarm of rectifier97 Enabled(1) or Disabled (0)"
    ::= {psAlarms2Masks 256}

a2VBV98Alarm OBJECT-TYPE
    SYNTAX   INTEGER{disabled(0), enabled(1)}
    MAX-ACCESS  read-write
    STATUS   current
    DESCRIPTION "Alarm of rectifier98 Enabled(1) or Disabled (0)"
    ::= {psAlarms2Masks 257}

a2VBV99Alarm OBJECT-TYPE
    SYNTAX   INTEGER{disabled(0), enabled(1)}
    MAX-ACCESS  read-write
    STATUS   current
    DESCRIPTION "Alarm of rectifier99 Enabled(1) or Disabled (0)"
    ::= {psAlarms2Masks 258}

a2VBV100Alarm OBJECT-TYPE
    SYNTAX   INTEGER{disabled(0), enabled(1)}
    MAX-ACCESS  read-write
    STATUS   current
    DESCRIPTION "Alarm of rectifier100 Enabled(1) or Disabled (0)"
    ::= {psAlarms2Masks 259}

a2VBV101Alarm OBJECT-TYPE
    SYNTAX   INTEGER{disabled(0), enabled(1)}
    MAX-ACCESS  read-write
    STATUS   current
    DESCRIPTION "Alarm of rectifier101 Enabled(1) or Disabled (0)"
    ::= {psAlarms2Masks 260}

a2VBV102Alarm OBJECT-TYPE
    SYNTAX   INTEGER{disabled(0), enabled(1)}
    MAX-ACCESS  read-write
    STATUS   current
    DESCRIPTION "Alarm of rectifier102 Enabled(1) or Disabled (0)"
    ::= {psAlarms2Masks 261}

a2VBV103Alarm OBJECT-TYPE
    SYNTAX   INTEGER{disabled(0), enabled(1)}
    MAX-ACCESS  read-write
    STATUS   current
    DESCRIPTION "Alarm of rectifier103 Enabled(1) or Disabled (0)"
    ::= {psAlarms2Masks 262}

a2VBV104Alarm OBJECT-TYPE
    SYNTAX   INTEGER{disabled(0), enabled(1)}
    MAX-ACCESS  read-write
    STATUS   current
    DESCRIPTION "Alarm of rectifier104 Enabled(1) or Disabled (0)"
    ::= {psAlarms2Masks 263}

a2VBV105Alarm OBJECT-TYPE
    SYNTAX   INTEGER{disabled(0), enabled(1)}
    MAX-ACCESS  read-write
    STATUS   current
    DESCRIPTION "Alarm of rectifier105 Enabled(1) or Disabled (0)"
    ::= {psAlarms2Masks 264}

a2VBV106Alarm OBJECT-TYPE
    SYNTAX   INTEGER{disabled(0), enabled(1)}
    MAX-ACCESS  read-write
    STATUS   current
    DESCRIPTION "Alarm of rectifier106 Enabled(1) or Disabled (0)"
    ::= {psAlarms2Masks 265}

a2VBV107Alarm OBJECT-TYPE
    SYNTAX   INTEGER{disabled(0), enabled(1)}
    MAX-ACCESS  read-write
    STATUS   current
    DESCRIPTION "Alarm of rectifier107 Enabled(1) or Disabled (0)"
    ::= {psAlarms2Masks 266}

a2VBV108Alarm OBJECT-TYPE
    SYNTAX   INTEGER{disabled(0), enabled(1)}
    MAX-ACCESS  read-write
    STATUS   current
    DESCRIPTION "Alarm of rectifier108 Enabled(1) or Disabled (0)"
    ::= {psAlarms2Masks 267}

a2VBV109Alarm OBJECT-TYPE
    SYNTAX   INTEGER{disabled(0), enabled(1)}
    MAX-ACCESS  read-write
    STATUS   current
    DESCRIPTION "Alarm of rectifier109 Enabled(1) or Disabled (0)"
    ::= {psAlarms2Masks 268}

a2VBV110Alarm OBJECT-TYPE
    SYNTAX   INTEGER{disabled(0), enabled(1)}
    MAX-ACCESS  read-write
    STATUS   current
    DESCRIPTION "Alarm of rectifier110 Enabled(1) or Disabled (0)"
    ::= {psAlarms2Masks 269}

a2VBV111Alarm OBJECT-TYPE
    SYNTAX   INTEGER{disabled(0), enabled(1)}
    MAX-ACCESS  read-write
    STATUS   current
    DESCRIPTION "Alarm of rectifier111 Enabled(1) or Disabled (0)"
    ::= {psAlarms2Masks 270}

a2VBV112Alarm OBJECT-TYPE
    SYNTAX   INTEGER{disabled(0), enabled(1)}
    MAX-ACCESS  read-write
    STATUS   current
    DESCRIPTION "Alarm of rectifier112 Enabled(1) or Disabled (0)"
    ::= {psAlarms2Masks 271}

a2VBV113Alarm OBJECT-TYPE
    SYNTAX   INTEGER{disabled(0), enabled(1)}
    MAX-ACCESS  read-write
    STATUS   current
    DESCRIPTION "Alarm of rectifier113 Enabled(1) or Disabled (0)"
    ::= {psAlarms2Masks 272}

a2VBV114Alarm OBJECT-TYPE
    SYNTAX   INTEGER{disabled(0), enabled(1)}
    MAX-ACCESS  read-write
    STATUS   current
    DESCRIPTION "Alarm of rectifier114 Enabled(1) or Disabled (0)"
    ::= {psAlarms2Masks 273}

a2VBV115Alarm OBJECT-TYPE
    SYNTAX   INTEGER{disabled(0), enabled(1)}
    MAX-ACCESS  read-write
    STATUS   current
    DESCRIPTION "Alarm of rectifier115 Enabled(1) or Disabled (0)"
    ::= {psAlarms2Masks 274}

a2VBV116Alarm OBJECT-TYPE
    SYNTAX   INTEGER{disabled(0), enabled(1)}
    MAX-ACCESS  read-write
    STATUS   current
    DESCRIPTION "Alarm of rectifier116 Enabled(1) or Disabled (0)"
    ::= {psAlarms2Masks 275}

a2VBV117Alarm OBJECT-TYPE
    SYNTAX   INTEGER{disabled(0), enabled(1)}
    MAX-ACCESS  read-write
    STATUS   current
    DESCRIPTION "Alarm of rectifier117 Enabled(1) or Disabled (0)"
    ::= {psAlarms2Masks 276}

a2VBV118Alarm OBJECT-TYPE
    SYNTAX   INTEGER{disabled(0), enabled(1)}
    MAX-ACCESS  read-write
    STATUS   current
    DESCRIPTION "Alarm of rectifier118 Enabled(1) or Disabled (0)"
    ::= {psAlarms2Masks 277}

a2VBV119Alarm OBJECT-TYPE
    SYNTAX   INTEGER{disabled(0), enabled(1)}
    MAX-ACCESS  read-write
    STATUS   current
    DESCRIPTION "Alarm of rectifier119 Enabled(1) or Disabled (0)"
    ::= {psAlarms2Masks 278}

a2VBV120Alarm OBJECT-TYPE
    SYNTAX   INTEGER{disabled(0), enabled(1)}
    MAX-ACCESS  read-write
    STATUS   current
    DESCRIPTION "Alarm of rectifier120 Enabled(1) or Disabled (0)"
    ::= {psAlarms2Masks 279}

a2VBV121Alarm OBJECT-TYPE
    SYNTAX   INTEGER{disabled(0), enabled(1)}
    MAX-ACCESS  read-write
    STATUS   current
    DESCRIPTION "Alarm of rectifier121 Enabled(1) or Disabled (0)"
    ::= {psAlarms2Masks 280}

a2VBV122Alarm OBJECT-TYPE
    SYNTAX   INTEGER{disabled(0), enabled(1)}
    MAX-ACCESS  read-write
    STATUS   current
    DESCRIPTION "Alarm of rectifier122 Enabled(1) or Disabled (0)"
    ::= {psAlarms2Masks 281}

a2VBV123Alarm OBJECT-TYPE
    SYNTAX   INTEGER{disabled(0), enabled(1)}
    MAX-ACCESS  read-write
    STATUS   current
    DESCRIPTION "Alarm of rectifier123 Enabled(1) or Disabled (0)"
    ::= {psAlarms2Masks 282}

a2VBV124Alarm OBJECT-TYPE
    SYNTAX   INTEGER{disabled(0), enabled(1)}
    MAX-ACCESS  read-write
    STATUS   current
    DESCRIPTION "Alarm of rectifier124 Enabled(1) or Disabled (0)"
    ::= {psAlarms2Masks 283}

a2VBV125Alarm OBJECT-TYPE
    SYNTAX   INTEGER{disabled(0), enabled(1)}
    MAX-ACCESS  read-write
    STATUS   current
    DESCRIPTION "Alarm of rectifier125 Enabled(1) or Disabled (0)"
    ::= {psAlarms2Masks 284}

a2VBV126Alarm OBJECT-TYPE
    SYNTAX   INTEGER{disabled(0), enabled(1)}
    MAX-ACCESS  read-write
    STATUS   current
    DESCRIPTION "Alarm of rectifier126 Enabled(1) or Disabled (0)"
    ::= {psAlarms2Masks 285}

a2VBV127Alarm OBJECT-TYPE
    SYNTAX   INTEGER{disabled(0), enabled(1)}
    MAX-ACCESS  read-write
    STATUS   current
    DESCRIPTION "Alarm of rectifier127 Enabled(1) or Disabled (0)"
    ::= {psAlarms2Masks 286}

a2VBV128Alarm OBJECT-TYPE
    SYNTAX   INTEGER{disabled(0), enabled(1)}
    MAX-ACCESS  read-write
    STATUS   current
    DESCRIPTION "Alarm of rectifier128 Enabled(1) or Disabled (0)"
    ::= {psAlarms2Masks 287}

a2VBV129Alarm OBJECT-TYPE
    SYNTAX   INTEGER{disabled(0), enabled(1)}
    MAX-ACCESS  read-write
    STATUS   current
    DESCRIPTION "Alarm of rectifier129 Enabled(1) or Disabled (0)"
    ::= {psAlarms2Masks 288}

a2VBV130Alarm OBJECT-TYPE
    SYNTAX   INTEGER{disabled(0), enabled(1)}
    MAX-ACCESS  read-write
    STATUS   current
    DESCRIPTION "Alarm of rectifier130 Enabled(1) or Disabled (0)"
    ::= {psAlarms2Masks 289}

a2VBV131Alarm OBJECT-TYPE
    SYNTAX   INTEGER{disabled(0), enabled(1)}
    MAX-ACCESS  read-write
    STATUS   current
    DESCRIPTION "Alarm of rectifier131 Enabled(1) or Disabled (0)"
    ::= {psAlarms2Masks 290}

a2VBV132Alarm OBJECT-TYPE
    SYNTAX   INTEGER{disabled(0), enabled(1)}
    MAX-ACCESS  read-write
    STATUS   current
    DESCRIPTION "Alarm of rectifier132 Enabled(1) or Disabled (0)"
    ::= {psAlarms2Masks 291}

a2VBV133Alarm OBJECT-TYPE
    SYNTAX   INTEGER{disabled(0), enabled(1)}
    MAX-ACCESS  read-write
    STATUS   current
    DESCRIPTION "Alarm of rectifier133 Enabled(1) or Disabled (0)"
    ::= {psAlarms2Masks 292}

a2VBV134Alarm OBJECT-TYPE
    SYNTAX   INTEGER{disabled(0), enabled(1)}
    MAX-ACCESS  read-write
    STATUS   current
    DESCRIPTION "Alarm of rectifier134 Enabled(1) or Disabled (0)"
    ::= {psAlarms2Masks 293}

a2VBV135Alarm OBJECT-TYPE
    SYNTAX   INTEGER{disabled(0), enabled(1)}
    MAX-ACCESS  read-write
    STATUS   current
    DESCRIPTION "Alarm of rectifier135 Enabled(1) or Disabled (0)"
    ::= {psAlarms2Masks 294}

a2VBV136Alarm OBJECT-TYPE
    SYNTAX   INTEGER{disabled(0), enabled(1)}
    MAX-ACCESS  read-write
    STATUS   current
    DESCRIPTION "Alarm of rectifier136 Enabled(1) or Disabled (0)"
    ::= {psAlarms2Masks 295}

a2VBV137Alarm OBJECT-TYPE
    SYNTAX   INTEGER{disabled(0), enabled(1)}
    MAX-ACCESS  read-write
    STATUS   current
    DESCRIPTION "Alarm of rectifier137 Enabled(1) or Disabled (0)"
    ::= {psAlarms2Masks 296}

a2VBV138Alarm OBJECT-TYPE
    SYNTAX   INTEGER{disabled(0), enabled(1)}
    MAX-ACCESS  read-write
    STATUS   current
    DESCRIPTION "Alarm of rectifier138 Enabled(1) or Disabled (0)"
    ::= {psAlarms2Masks 297}

a2VBV139Alarm OBJECT-TYPE
    SYNTAX   INTEGER{disabled(0), enabled(1)}
    MAX-ACCESS  read-write
    STATUS   current
    DESCRIPTION "Alarm of rectifier139 Enabled(1) or Disabled (0)"
    ::= {psAlarms2Masks 298}

a2VBV140Alarm OBJECT-TYPE
    SYNTAX   INTEGER{disabled(0), enabled(1)}
    MAX-ACCESS  read-write
    STATUS   current
    DESCRIPTION "Alarm of rectifier140 Enabled(1) or Disabled (0)"
    ::= {psAlarms2Masks 299}

a2VBV141Alarm OBJECT-TYPE
    SYNTAX   INTEGER{disabled(0), enabled(1)}
    MAX-ACCESS  read-write
    STATUS   current
    DESCRIPTION "Alarm of rectifier141 Enabled(1) or Disabled (0)"
    ::= {psAlarms2Masks 300}

a2VBV142Alarm OBJECT-TYPE
    SYNTAX   INTEGER{disabled(0), enabled(1)}
    MAX-ACCESS  read-write
    STATUS   current
    DESCRIPTION "Alarm of rectifier142 Enabled(1) or Disabled (0)"
    ::= {psAlarms2Masks 301}

a2VBV143Alarm OBJECT-TYPE
    SYNTAX   INTEGER{disabled(0), enabled(1)}
    MAX-ACCESS  read-write
    STATUS   current
    DESCRIPTION "Alarm of rectifier143 Enabled(1) or Disabled (0)"
    ::= {psAlarms2Masks 302}

a2VBV144Alarm OBJECT-TYPE
    SYNTAX   INTEGER{disabled(0), enabled(1)}
    MAX-ACCESS  read-write
    STATUS   current
    DESCRIPTION "Alarm of rectifier144 Enabled(1) or Disabled (0)"
    ::= {psAlarms2Masks 303}

a2VBV145Alarm OBJECT-TYPE
    SYNTAX   INTEGER{disabled(0), enabled(1)}
    MAX-ACCESS  read-write
    STATUS   current
    DESCRIPTION "Alarm of rectifier145 Enabled(1) or Disabled (0)"
    ::= {psAlarms2Masks 304}

a2VBV146Alarm OBJECT-TYPE
    SYNTAX   INTEGER{disabled(0), enabled(1)}
    MAX-ACCESS  read-write
    STATUS   current
    DESCRIPTION "Alarm of rectifier146 Enabled(1) or Disabled (0)"
    ::= {psAlarms2Masks 305}

a2VBV147Alarm OBJECT-TYPE
    SYNTAX   INTEGER{disabled(0), enabled(1)}
    MAX-ACCESS  read-write
    STATUS   current
    DESCRIPTION "Alarm of rectifier147 Enabled(1) or Disabled (0)"
    ::= {psAlarms2Masks 306}

a2VBV148Alarm OBJECT-TYPE
    SYNTAX   INTEGER{disabled(0), enabled(1)}
    MAX-ACCESS  read-write
    STATUS   current
    DESCRIPTION "Alarm of rectifier148 Enabled(1) or Disabled (0)"
    ::= {psAlarms2Masks 307}

a2VBV149Alarm OBJECT-TYPE
    SYNTAX   INTEGER{disabled(0), enabled(1)}
    MAX-ACCESS  read-write
    STATUS   current
    DESCRIPTION "Alarm of rectifier149 Enabled(1) or Disabled (0)"
    ::= {psAlarms2Masks 308}

a2VBV150Alarm OBJECT-TYPE
    SYNTAX   INTEGER{disabled(0), enabled(1)}
    MAX-ACCESS  read-write
    STATUS   current
    DESCRIPTION "Alarm of rectifier150 Enabled(1) or Disabled (0)"
    ::= {psAlarms2Masks 309}

a2VBV151Alarm OBJECT-TYPE
    SYNTAX   INTEGER{disabled(0), enabled(1)}
    MAX-ACCESS  read-write
    STATUS   current
    DESCRIPTION "Alarm of rectifier151 Enabled(1) or Disabled (0)"
    ::= {psAlarms2Masks 310}

a2VBV152Alarm OBJECT-TYPE
    SYNTAX   INTEGER{disabled(0), enabled(1)}
    MAX-ACCESS  read-write
    STATUS   current
    DESCRIPTION "Alarm of rectifier152 Enabled(1) or Disabled (0)"
    ::= {psAlarms2Masks 311}

a2VBV153Alarm OBJECT-TYPE
    SYNTAX   INTEGER{disabled(0), enabled(1)}
    MAX-ACCESS  read-write
    STATUS   current
    DESCRIPTION "Alarm of rectifier153 Enabled(1) or Disabled (0)"
    ::= {psAlarms2Masks 312}

a2VBV154Alarm OBJECT-TYPE
    SYNTAX   INTEGER{disabled(0), enabled(1)}
    MAX-ACCESS  read-write
    STATUS   current
    DESCRIPTION "Alarm of rectifier154 Enabled(1) or Disabled (0)"
    ::= {psAlarms2Masks 313}

a2VBV155Alarm OBJECT-TYPE
    SYNTAX   INTEGER{disabled(0), enabled(1)}
    MAX-ACCESS  read-write
    STATUS   current
    DESCRIPTION "Alarm of rectifier155 Enabled(1) or Disabled (0)"
    ::= {psAlarms2Masks 314}

a2VBV156Alarm OBJECT-TYPE
    SYNTAX   INTEGER{disabled(0), enabled(1)}
    MAX-ACCESS  read-write
    STATUS   current
    DESCRIPTION "Alarm of rectifier156 Enabled(1) or Disabled (0)"
    ::= {psAlarms2Masks 315}

a2VBV157Alarm OBJECT-TYPE
    SYNTAX   INTEGER{disabled(0), enabled(1)}
    MAX-ACCESS  read-write
    STATUS   current
    DESCRIPTION "Alarm of rectifier157 Enabled(1) or Disabled (0)"
    ::= {psAlarms2Masks 316}

a2VBV158Alarm OBJECT-TYPE
    SYNTAX   INTEGER{disabled(0), enabled(1)}
    MAX-ACCESS  read-write
    STATUS   current
    DESCRIPTION "Alarm of rectifier158 Enabled(1) or Disabled (0)"
    ::= {psAlarms2Masks 317}

a2VBV159Alarm OBJECT-TYPE
    SYNTAX   INTEGER{disabled(0), enabled(1)}
    MAX-ACCESS  read-write
    STATUS   current
    DESCRIPTION "Alarm of rectifier159 Enabled(1) or Disabled (0)"
    ::= {psAlarms2Masks 318}

a2VBV160Alarm OBJECT-TYPE
    SYNTAX   INTEGER{disabled(0), enabled(1)}
    MAX-ACCESS  read-write
    STATUS   current
    DESCRIPTION "Alarm of rectifier160 Enabled(1) or Disabled (0)"
    ::= {psAlarms2Masks 319}

a2VBV161Alarm OBJECT-TYPE
    SYNTAX   INTEGER{disabled(0), enabled(1)}
    MAX-ACCESS  read-write
    STATUS   current
    DESCRIPTION "Alarm of rectifier161 Enabled(1) or Disabled (0)"
    ::= {psAlarms2Masks 320}

a2VBV162Alarm OBJECT-TYPE
    SYNTAX   INTEGER{disabled(0), enabled(1)}
    MAX-ACCESS  read-write
    STATUS   current
    DESCRIPTION "Alarm of rectifier162 Enabled(1) or Disabled (0)"
    ::= {psAlarms2Masks 321}

a2VBV163Alarm OBJECT-TYPE
    SYNTAX   INTEGER{disabled(0), enabled(1)}
    MAX-ACCESS  read-write
    STATUS   current
    DESCRIPTION "Alarm of rectifier163 Enabled(1) or Disabled (0)"
    ::= {psAlarms2Masks 322}

a2VBV164Alarm OBJECT-TYPE
    SYNTAX   INTEGER{disabled(0), enabled(1)}
    MAX-ACCESS  read-write
    STATUS   current
    DESCRIPTION "Alarm of rectifier164 Enabled(1) or Disabled (0)"
    ::= {psAlarms2Masks 323}

a2VBV165Alarm OBJECT-TYPE
    SYNTAX   INTEGER{disabled(0), enabled(1)}
    MAX-ACCESS  read-write
    STATUS   current
    DESCRIPTION "Alarm of rectifier165 Enabled(1) or Disabled (0)"
    ::= {psAlarms2Masks 324}

a2VBV166Alarm OBJECT-TYPE
    SYNTAX   INTEGER{disabled(0), enabled(1)}
    MAX-ACCESS  read-write
    STATUS   current
    DESCRIPTION "Alarm of rectifier166 Enabled(1) or Disabled (0)"
    ::= {psAlarms2Masks 325}

a2VBV167Alarm OBJECT-TYPE
    SYNTAX   INTEGER{disabled(0), enabled(1)}
    MAX-ACCESS  read-write
    STATUS   current
    DESCRIPTION "Alarm of rectifier167 Enabled(1) or Disabled (0)"
    ::= {psAlarms2Masks 326}

a2VBV168Alarm OBJECT-TYPE
    SYNTAX   INTEGER{disabled(0), enabled(1)}
    MAX-ACCESS  read-write
    STATUS   current
    DESCRIPTION "Alarm of rectifier168 Enabled(1) or Disabled (0)"
    ::= {psAlarms2Masks 327}

a2VBV169Alarm OBJECT-TYPE
    SYNTAX   INTEGER{disabled(0), enabled(1)}
    MAX-ACCESS  read-write
    STATUS   current
    DESCRIPTION "Alarm of rectifier169 Enabled(1) or Disabled (0)"
    ::= {psAlarms2Masks 328}

a2VBV170Alarm OBJECT-TYPE
    SYNTAX   INTEGER{disabled(0), enabled(1)}
    MAX-ACCESS  read-write
    STATUS   current
    DESCRIPTION "Alarm of rectifier170 Enabled(1) or Disabled (0)"
    ::= {psAlarms2Masks 329}

a2VBV171Alarm OBJECT-TYPE
    SYNTAX   INTEGER{disabled(0), enabled(1)}
    MAX-ACCESS  read-write
    STATUS   current
    DESCRIPTION "Alarm of rectifier171 Enabled(1) or Disabled (0)"
    ::= {psAlarms2Masks 330}

a2VBV172Alarm OBJECT-TYPE
    SYNTAX   INTEGER{disabled(0), enabled(1)}
    MAX-ACCESS  read-write
    STATUS   current
    DESCRIPTION "Alarm of rectifier172 Enabled(1) or Disabled (0)"
    ::= {psAlarms2Masks 331}

a2VBV173Alarm OBJECT-TYPE
    SYNTAX   INTEGER{disabled(0), enabled(1)}
    MAX-ACCESS  read-write
    STATUS   current
    DESCRIPTION "Alarm of rectifier173 Enabled(1) or Disabled (0)"
    ::= {psAlarms2Masks 332}

a2VBV174Alarm OBJECT-TYPE
    SYNTAX   INTEGER{disabled(0), enabled(1)}
    MAX-ACCESS  read-write
    STATUS   current
    DESCRIPTION "Alarm of rectifier174 Enabled(1) or Disabled (0)"
    ::= {psAlarms2Masks 333}

a2VBV175Alarm OBJECT-TYPE
    SYNTAX   INTEGER{disabled(0), enabled(1)}
    MAX-ACCESS  read-write
    STATUS   current
    DESCRIPTION "Alarm of rectifier175 Enabled(1) or Disabled (0)"
    ::= {psAlarms2Masks 334}

a2VBV176Alarm OBJECT-TYPE
    SYNTAX   INTEGER{disabled(0), enabled(1)}
    MAX-ACCESS  read-write
    STATUS   current
    DESCRIPTION "Alarm of rectifier176 Enabled(1) or Disabled (0)"
    ::= {psAlarms2Masks 335}

a2VBV177Alarm OBJECT-TYPE
    SYNTAX   INTEGER{disabled(0), enabled(1)}
    MAX-ACCESS  read-write
    STATUS   current
    DESCRIPTION "Alarm of rectifier177 Enabled(1) or Disabled (0)"
    ::= {psAlarms2Masks 336}

a2VBV178Alarm OBJECT-TYPE
    SYNTAX   INTEGER{disabled(0), enabled(1)}
    MAX-ACCESS  read-write
    STATUS   current
    DESCRIPTION "Alarm of rectifier178 Enabled(1) or Disabled (0)"
    ::= {psAlarms2Masks 337}

a2VBV179Alarm OBJECT-TYPE
    SYNTAX   INTEGER{disabled(0), enabled(1)}
    MAX-ACCESS  read-write
    STATUS   current
    DESCRIPTION "Alarm of rectifier179 Enabled(1) or Disabled (0)"
    ::= {psAlarms2Masks 338}

a2VBV180Alarm OBJECT-TYPE
    SYNTAX   INTEGER{disabled(0), enabled(1)}
    MAX-ACCESS  read-write
    STATUS   current
    DESCRIPTION "Alarm of rectifier180 Enabled(1) or Disabled (0)"
    ::= {psAlarms2Masks 339}

a2VBVNoReserve OBJECT-TYPE
    SYNTAX   INTEGER{disabled(0), enabled(1)}
    MAX-ACCESS  read-write
    STATUS   current
    DESCRIPTION "Enabled(1) or Disabled (0)"
    ::= {psAlarms2Masks 340}

a2VBVHighEfficiency OBJECT-TYPE
    SYNTAX   INTEGER{disabled(0), enabled(1)}
    MAX-ACCESS  read-write
    STATUS   current
    DESCRIPTION "Enabled(1) or Disabled (0)"
    ::= {psAlarms2Masks 341}

--PhasesAlarm in psAlarms2Masks
a2Phase1Alarm OBJECT-TYPE
    SYNTAX   INTEGER{disabled(0), enabled(1)}
    MAX-ACCESS  read-write
    STATUS   current
    DESCRIPTION "Enabled(1) or Disabled (0)"
    ::= {psAlarms2Masks 352}

a2Phase2Alarm OBJECT-TYPE
    SYNTAX   INTEGER{disabled(0), enabled(1)}
    MAX-ACCESS  read-write
    STATUS   current
    DESCRIPTION "Enabled(1) or Disabled (0)"
    ::= {psAlarms2Masks 353}

a2Phase3Alarm OBJECT-TYPE
    SYNTAX   INTEGER{disabled(0), enabled(1)}
    MAX-ACCESS  read-write
    STATUS   current
    DESCRIPTION "Enabled(1) or Disabled (0)"
    ::= {psAlarms2Masks 354}

a2MainsSensorError OBJECT-TYPE
    SYNTAX   INTEGER{disabled(0), enabled(1)}
    MAX-ACCESS  read-write
    STATUS   current
    DESCRIPTION "Enabled(1) or Disabled (0)"
    ::= {psAlarms2Masks 355}

a2LightProtectionAlarm OBJECT-TYPE
    SYNTAX   INTEGER{disabled(0), enabled(1)}
    MAX-ACCESS  read-write
    STATUS   current
    DESCRIPTION "Enabled(1) or Disabled (0)"
    ::= {psAlarms2Masks 356}

--Ambience Temperature in psAlarms2Masks
a2LowTemperature OBJECT-TYPE
    SYNTAX   INTEGER{disabled(0), enabled(1)}
    MAX-ACCESS  read-write
    STATUS   current
    DESCRIPTION "Enabled(1) or Disabled (0)"
    ::= {psAlarms2Masks 384}

a2HighTemperature OBJECT-TYPE
    SYNTAX   INTEGER{disabled(0), enabled(1)}
    MAX-ACCESS  read-write
    STATUS   current
    DESCRIPTION "Enabled(1) or Disabled (0)"
    ::= {psAlarms2Masks 385}

a2TemperatureSensorError OBJECT-TYPE
    SYNTAX   INTEGER{disabled(0), enabled(1)}
    MAX-ACCESS  read-write
    STATUS   current
    DESCRIPTION "Enabled(1) or Disabled (0)"
    ::= {psAlarms2Masks 386}

--DryContacts in psAlarms2Masks
a2DryContact1 OBJECT-TYPE
    SYNTAX   INTEGER{disabled(0), enabled(1)}
    MAX-ACCESS  read-write
    STATUS   current
    DESCRIPTION "Enabled(1) or Disabled (0)"
    ::= {psAlarms2Masks 416}

a2DryContact2 OBJECT-TYPE
    SYNTAX   INTEGER{disabled(0), enabled(1)}
    MAX-ACCESS  read-write
    STATUS   current
    DESCRIPTION "Enabled(1) or Disabled (0)"
    ::= {psAlarms2Masks 417}

a2DryContact3 OBJECT-TYPE
    SYNTAX   INTEGER{disabled(0), enabled(1)}
    MAX-ACCESS  read-write
    STATUS   current
    DESCRIPTION "Enabled(1) or Disabled (0)"
    ::= {psAlarms2Masks 418}

a2DryContact4 OBJECT-TYPE
    SYNTAX   INTEGER{disabled(0), enabled(1)}
    MAX-ACCESS  read-write
    STATUS   current
    DESCRIPTION "Enabled(1) or Disabled (0)"
    ::= {psAlarms2Masks 419}

a2DryContact5 OBJECT-TYPE
    SYNTAX   INTEGER{disabled(0), enabled(1)}
    MAX-ACCESS  read-write
    STATUS   current
    DESCRIPTION "Enabled(1) or Disabled (0)"
    ::= {psAlarms2Masks 420}

a2DryContact6 OBJECT-TYPE
    SYNTAX   INTEGER{disabled(0), enabled(1)}
    MAX-ACCESS  read-write
    STATUS   current
    DESCRIPTION "Enabled(1) or Disabled (0)"
    ::= {psAlarms2Masks 421}

a2DryContact7 OBJECT-TYPE
    SYNTAX   INTEGER{disabled(0), enabled(1)}
    MAX-ACCESS  read-write
    STATUS   current
    DESCRIPTION "Enabled(1) or Disabled (0)"
    ::= {psAlarms2Masks 422}

a2DryContact8 OBJECT-TYPE
    SYNTAX   INTEGER{disabled(0), enabled(1)}
    MAX-ACCESS  read-write
    STATUS   current
    DESCRIPTION "Enabled(1) or Disabled (0)"
    ::= {psAlarms2Masks 423}

a2DryContact9 OBJECT-TYPE
    SYNTAX   INTEGER{disabled(0), enabled(1)}
    MAX-ACCESS  read-write
    STATUS   current
    DESCRIPTION "Enabled(1) or Disabled (0)"
    ::= {psAlarms2Masks 424}

a2DryContact10 OBJECT-TYPE
    SYNTAX   INTEGER{disabled(0), enabled(1)}
    MAX-ACCESS  read-write
    STATUS   current
    DESCRIPTION "Enabled(1) or Disabled (0)"
    ::= {psAlarms2Masks 425}

a2DryContact11 OBJECT-TYPE
    SYNTAX   INTEGER{disabled(0), enabled(1)}
    MAX-ACCESS  read-write
    STATUS   current
    DESCRIPTION "Enabled(1) or Disabled (0)"
    ::= {psAlarms2Masks 426}

a2DryContact12 OBJECT-TYPE
    SYNTAX   INTEGER{disabled(0), enabled(1)}
    MAX-ACCESS  read-write
    STATUS   current
    DESCRIPTION "Enabled(1) or Disabled (0)"
    ::= {psAlarms2Masks 427}

a2DryContact13 OBJECT-TYPE
    SYNTAX   INTEGER{disabled(0), enabled(1)}
    MAX-ACCESS  read-write
    STATUS   current
    DESCRIPTION "Enabled(1) or Disabled (0)"
    ::= {psAlarms2Masks 428}

a2DryContact14 OBJECT-TYPE
    SYNTAX   INTEGER{disabled(0), enabled(1)}
    MAX-ACCESS  read-write
    STATUS   current
    DESCRIPTION "Enabled(1) or Disabled (0)"
    ::= {psAlarms2Masks 429}

a2DryContact15 OBJECT-TYPE
    SYNTAX   INTEGER{disabled(0), enabled(1)}
    MAX-ACCESS  read-write
    STATUS   current
    DESCRIPTION "Enabled(1) or Disabled (0)"
    ::= {psAlarms2Masks 430}

a2DryContact16 OBJECT-TYPE
    SYNTAX   INTEGER{disabled(0), enabled(1)}
    MAX-ACCESS  read-write
    STATUS   current
    DESCRIPTION "Enabled(1) or Disabled (0)"
    ::= {psAlarms2Masks 431}

-----------------------------------------------------------
a2BatteryLiIonAlarm OBJECT-TYPE  
    SYNTAX   INTEGER{disabled(0), enabled(1)}
    MAX-ACCESS  read-write
    STATUS   current
    DESCRIPTION "Enabled(1) or Disabled (0)"
    ::= {psAlarms2Masks 480}

--нет связи с BMS
a2BatteryBMSComFail OBJECT-TYPE  
    SYNTAX   INTEGER{disabled(0), enabled(1)}
    MAX-ACCESS  read-write
    STATUS   current
    DESCRIPTION "Enabled(1) or Disabled (0)"
    ::= {psAlarms2Masks 481}
-----------------------------------------------------------

--InternalErrors in psRelay1Masks
r1InternallError OBJECT-TYPE
    SYNTAX   INTEGER{disabled(0), enabled(1)}
    MAX-ACCESS  read-write
    STATUS   current
    DESCRIPTION "Enabled(1) or Disabled (0)"
    ::= {psRelay1Masks 1}

--OutputAlarms in psRelay1Masks
r1LoadUnderVoltageAlarm OBJECT-TYPE
    SYNTAX   INTEGER{disabled(0), enabled(1)}
    MAX-ACCESS  read-write
    STATUS   current
    DESCRIPTION "Enabled(1) or Disabled (0)"
    ::= {psRelay1Masks 32}

r1LoadOverVoltageAlarm OBJECT-TYPE
    SYNTAX   INTEGER{disabled(0), enabled(1)}
    MAX-ACCESS  read-write
    STATUS   current
    DESCRIPTION "Enabled(1) or Disabled (0)"
    ::= {psRelay1Masks 33}

r1Termocompensation OBJECT-TYPE
    SYNTAX   INTEGER{disabled(0), enabled(1)}
    MAX-ACCESS  read-write
    STATUS   current
    DESCRIPTION "Enabled(1) or Disabled (0)"
    ::= {psRelay1Masks 34}

--LoadFuses in psRelay1Masks
r1LoadFuses1 OBJECT-TYPE
    SYNTAX   INTEGER{disabled(0), enabled(1)}
    MAX-ACCESS  read-write
    STATUS   current
    DESCRIPTION "Enabled(1) or Disabled (0)"
    ::= {psRelay1Masks 35}

r1LoadFuses2 OBJECT-TYPE
    SYNTAX   INTEGER{disabled(0), enabled(1)}
    MAX-ACCESS  read-write
    STATUS   current
    DESCRIPTION "Enabled(1) or Disabled (0)"
    ::= {psRelay1Masks 36}

r1LoadFuses3 OBJECT-TYPE
    SYNTAX   INTEGER{disabled(0), enabled(1)}
    MAX-ACCESS  read-write
    STATUS   current
    DESCRIPTION "Enabled(1) or Disabled (0)"
    ::= {psRelay1Masks 37}

r1LoadFuses4 OBJECT-TYPE
    SYNTAX   INTEGER{disabled(0), enabled(1)}
    MAX-ACCESS  read-write
    STATUS   current
    DESCRIPTION "Enabled(1) or Disabled (0)"
    ::= {psRelay1Masks 38}

r1LoadFuses5 OBJECT-TYPE
    SYNTAX   INTEGER{disabled(0), enabled(1)}
    MAX-ACCESS  read-write
    STATUS   current
    DESCRIPTION "Enabled(1) or Disabled (0)"
    ::= {psRelay1Masks 39}

r1LoadFuses6 OBJECT-TYPE
    SYNTAX   INTEGER{disabled(0), enabled(1)}
    MAX-ACCESS  read-write
    STATUS   current
    DESCRIPTION "Enabled(1) or Disabled (0)"
    ::= {psRelay1Masks 40}

r1LoadFuses7 OBJECT-TYPE
    SYNTAX   INTEGER{disabled(0), enabled(1)}
    MAX-ACCESS  read-write
    STATUS   current
    DESCRIPTION "Enabled(1) or Disabled (0)"
    ::= {psRelay1Masks 41}

r1LoadFuses8 OBJECT-TYPE
    SYNTAX   INTEGER{disabled(0), enabled(1)}
    MAX-ACCESS  read-write
    STATUS   current
    DESCRIPTION "Enabled(1) or Disabled (0)"
    ::= {psRelay1Masks 42}

r1LoadFuses9 OBJECT-TYPE
    SYNTAX   INTEGER{disabled(0), enabled(1)}
    MAX-ACCESS  read-write
    STATUS   current
    DESCRIPTION "Enabled(1) or Disabled (0)"
    ::= {psRelay1Masks 43}

r1LoadFuses10 OBJECT-TYPE
    SYNTAX   INTEGER{disabled(0), enabled(1)}
    MAX-ACCESS  read-write
    STATUS   current
    DESCRIPTION "Enabled(1) or Disabled (0)"
    ::= {psRelay1Masks 44}

r1LoadFuses11 OBJECT-TYPE
    SYNTAX   INTEGER{disabled(0), enabled(1)}
    MAX-ACCESS  read-write
    STATUS   current
    DESCRIPTION "Enabled(1) or Disabled (0)"
    ::= {psRelay1Masks 45}

r1LoadFuses12 OBJECT-TYPE
    SYNTAX   INTEGER{disabled(0), enabled(1)}
    MAX-ACCESS  read-write
    STATUS   current
    DESCRIPTION "Enabled(1) or Disabled (0)"
    ::= {psRelay1Masks 46}

r1LoadFuses13 OBJECT-TYPE
    SYNTAX   INTEGER{disabled(0), enabled(1)}
    MAX-ACCESS  read-write
    STATUS   current
    DESCRIPTION "Enabled(1) or Disabled (0)"
    ::= {psRelay1Masks 47}

r1LoadFuses14 OBJECT-TYPE
    SYNTAX   INTEGER{disabled(0), enabled(1)}
    MAX-ACCESS  read-write
    STATUS   current
    DESCRIPTION "Enabled(1) or Disabled (0)"
    ::= {psRelay1Masks 48}

r1LoadFuses15 OBJECT-TYPE
    SYNTAX   INTEGER{disabled(0), enabled(1)}
    MAX-ACCESS  read-write
    STATUS   current
    DESCRIPTION "Enabled(1) or Disabled (0)"
    ::= {psRelay1Masks 49}

r1LoadFuses16 OBJECT-TYPE
    SYNTAX   INTEGER{disabled(0), enabled(1)}
    MAX-ACCESS  read-write
    STATUS   current
    DESCRIPTION "Enabled(1) or Disabled (0)"
    ::= {psRelay1Masks 50}

r1LoadFuses17 OBJECT-TYPE
    SYNTAX   INTEGER{disabled(0), enabled(1)}
    MAX-ACCESS  read-write
    STATUS   current
    DESCRIPTION "Enabled(1) or Disabled (0)"
    ::= {psRelay1Masks 51}

r1LoadFuses18 OBJECT-TYPE
    SYNTAX   INTEGER{disabled(0), enabled(1)}
    MAX-ACCESS  read-write
    STATUS   current
    DESCRIPTION "Enabled(1) or Disabled (0)"
    ::= {psRelay1Masks 52}

r1LoadFuses19 OBJECT-TYPE
    SYNTAX   INTEGER{disabled(0), enabled(1)}
    MAX-ACCESS  read-write
    STATUS   current
    DESCRIPTION "Enabled(1) or Disabled (0)"
    ::= {psRelay1Masks 53}

r1LoadFuses20 OBJECT-TYPE
    SYNTAX   INTEGER{disabled(0), enabled(1)}
    MAX-ACCESS  read-write
    STATUS   current
    DESCRIPTION "Enabled(1) or Disabled (0)"
    ::= {psRelay1Masks 54}

r1LoadFuses21 OBJECT-TYPE
    SYNTAX   INTEGER{disabled(0), enabled(1)}
    MAX-ACCESS  read-write
    STATUS   current
    DESCRIPTION "Enabled(1) or Disabled (0)"
    ::= {psRelay1Masks 55}

r1LoadFuses22 OBJECT-TYPE
    SYNTAX   INTEGER{disabled(0), enabled(1)}
    MAX-ACCESS  read-write
    STATUS   current
    DESCRIPTION "Enabled(1) or Disabled (0)"
    ::= {psRelay1Masks 56}

r1LoadFuses23 OBJECT-TYPE
    SYNTAX   INTEGER{disabled(0), enabled(1)}
    MAX-ACCESS  read-write
    STATUS   current
    DESCRIPTION "Enabled(1) or Disabled (0)"
    ::= {psRelay1Masks 57}

r1LoadFuses24 OBJECT-TYPE
    SYNTAX   INTEGER{disabled(0), enabled(1)}
    MAX-ACCESS  read-write
    STATUS   current
    DESCRIPTION "Enabled(1) or Disabled (0)"
    ::= {psRelay1Masks 58}

r1LoadFuses25 OBJECT-TYPE
    SYNTAX   INTEGER{disabled(0), enabled(1)}
    MAX-ACCESS  read-write
    STATUS   current
    DESCRIPTION "Enabled(1) or Disabled (0)"
    ::= {psRelay1Masks 59}

r1LoadFuses26 OBJECT-TYPE
    SYNTAX   INTEGER{disabled(0), enabled(1)}
    MAX-ACCESS  read-write
    STATUS   current
    DESCRIPTION "Enabled(1) or Disabled (0)"
    ::= {psRelay1Masks 60}

r1LoadFuses27 OBJECT-TYPE
    SYNTAX   INTEGER{disabled(0), enabled(1)}
    MAX-ACCESS  read-write
    STATUS   current
    DESCRIPTION "Enabled(1) or Disabled (0)"
    ::= {psRelay1Masks 61}

r1LoadFuses28 OBJECT-TYPE
    SYNTAX   INTEGER{disabled(0), enabled(1)}
    MAX-ACCESS  read-write
    STATUS   current
    DESCRIPTION "Enabled(1) or Disabled (0)"
    ::= {psRelay1Masks 62}

r1LoadFuses29 OBJECT-TYPE
    SYNTAX   INTEGER{disabled(0), enabled(1)}
    MAX-ACCESS  read-write
    STATUS   current
    DESCRIPTION "Enabled(1) or Disabled (0)"
    ::= {psRelay1Masks 63}

r1LoadFuses30 OBJECT-TYPE
    SYNTAX   INTEGER{disabled(0), enabled(1)}
    MAX-ACCESS  read-write
    STATUS   current
    DESCRIPTION "Enabled(1) or Disabled (0)"
    ::= {psRelay1Masks 64}

r1LoadFuses31 OBJECT-TYPE
    SYNTAX   INTEGER{disabled(0), enabled(1)}
    MAX-ACCESS  read-write
    STATUS   current
    DESCRIPTION "Enabled(1) or Disabled (0)"
    ::= {psRelay1Masks 65}

r1LoadFuses32 OBJECT-TYPE
    SYNTAX   INTEGER{disabled(0), enabled(1)}
    MAX-ACCESS  read-write
    STATUS   current
    DESCRIPTION "Enabled(1) or Disabled (0)"
    ::= {psRelay1Masks 66}

r1LoadFuses33 OBJECT-TYPE
    SYNTAX   INTEGER{disabled(0), enabled(1)}
    MAX-ACCESS  read-write
    STATUS   current
    DESCRIPTION "Enabled(1) or Disabled (0)"
    ::= {psRelay1Masks 67}

r1LoadFuses34 OBJECT-TYPE
    SYNTAX   INTEGER{disabled(0), enabled(1)}
    MAX-ACCESS  read-write
    STATUS   current
    DESCRIPTION "Enabled(1) or Disabled (0)"
    ::= {psRelay1Masks 68}

r1LoadFuses35 OBJECT-TYPE
    SYNTAX   INTEGER{disabled(0), enabled(1)}
    MAX-ACCESS  read-write
    STATUS   current
    DESCRIPTION "Enabled(1) or Disabled (0)"
    ::= {psRelay1Masks 69}

r1LoadFuses36 OBJECT-TYPE
    SYNTAX   INTEGER{disabled(0), enabled(1)}
    MAX-ACCESS  read-write
    STATUS   current
    DESCRIPTION "Enabled(1) or Disabled (0)"
    ::= {psRelay1Masks 70}

r1LoadFuses37 OBJECT-TYPE
    SYNTAX   INTEGER{disabled(0), enabled(1)}
    MAX-ACCESS  read-write
    STATUS   current
    DESCRIPTION "Enabled(1) or Disabled (0)"
    ::= {psRelay1Masks 71}

r1LoadFuses38 OBJECT-TYPE
    SYNTAX   INTEGER{disabled(0), enabled(1)}
    MAX-ACCESS  read-write
    STATUS   current
    DESCRIPTION "Enabled(1) or Disabled (0)"
    ::= {psRelay1Masks 72}

r1LoadFuses39 OBJECT-TYPE
    SYNTAX   INTEGER{disabled(0), enabled(1)}
    MAX-ACCESS  read-write
    STATUS   current
    DESCRIPTION "Enabled(1) or Disabled (0)"
    ::= {psRelay1Masks 73}

r1LoadFuses40 OBJECT-TYPE
    SYNTAX   INTEGER{disabled(0), enabled(1)}
    MAX-ACCESS  read-write
    STATUS   current
    DESCRIPTION "Enabled(1) or Disabled (0)"
    ::= {psRelay1Masks 74}

r1LoadFuses41 OBJECT-TYPE
    SYNTAX   INTEGER{disabled(0), enabled(1)}
    MAX-ACCESS  read-write
    STATUS   current
    DESCRIPTION "Enabled(1) or Disabled (0)"
    ::= {psRelay1Masks 75}

r1LoadFuses42 OBJECT-TYPE
    SYNTAX   INTEGER{disabled(0), enabled(1)}
    MAX-ACCESS  read-write
    STATUS   current
    DESCRIPTION "Enabled(1) or Disabled (0)"
    ::= {psRelay1Masks 76}

r1LoadFuses43 OBJECT-TYPE
    SYNTAX   INTEGER{disabled(0), enabled(1)}
    MAX-ACCESS  read-write
    STATUS   current
    DESCRIPTION "Enabled(1) or Disabled (0)"
    ::= {psRelay1Masks 77}

r1LoadFuses44 OBJECT-TYPE
    SYNTAX   INTEGER{disabled(0), enabled(1)}
    MAX-ACCESS  read-write
    STATUS   current
    DESCRIPTION "Enabled(1) or Disabled (0)"
    ::= {psRelay1Masks 78}

r1LoadFuses45 OBJECT-TYPE
    SYNTAX   INTEGER{disabled(0), enabled(1)}
    MAX-ACCESS  read-write
    STATUS   current
    DESCRIPTION "Enabled(1) or Disabled (0)"
    ::= {psRelay1Masks 79}

r1LoadFuses46 OBJECT-TYPE
    SYNTAX   INTEGER{disabled(0), enabled(1)}
    MAX-ACCESS  read-write
    STATUS   current
    DESCRIPTION "Enabled(1) or Disabled (0)"
    ::= {psRelay1Masks 80}

r1LoadFuses47 OBJECT-TYPE
    SYNTAX   INTEGER{disabled(0), enabled(1)}
    MAX-ACCESS  read-write
    STATUS   current
    DESCRIPTION "Enabled(1) or Disabled (0)"
    ::= {psRelay1Masks 81}

r1LoadFuses48 OBJECT-TYPE
    SYNTAX   INTEGER{disabled(0), enabled(1)}
    MAX-ACCESS  read-write
    STATUS   current
    DESCRIPTION "Enabled(1) or Disabled (0)"
    ::= {psRelay1Masks 82}

r1LoadFuses49 OBJECT-TYPE
    SYNTAX   INTEGER{disabled(0), enabled(1)}
    MAX-ACCESS  read-write
    STATUS   current
    DESCRIPTION "Enabled(1) or Disabled (0)"
    ::= {psRelay1Masks 83}

r1LoadFuses50 OBJECT-TYPE
    SYNTAX   INTEGER{disabled(0), enabled(1)}
    MAX-ACCESS  read-write
    STATUS   current
    DESCRIPTION "Enabled(1) or Disabled (0)"
    ::= {psRelay1Masks 84}

r1LoadFuses51 OBJECT-TYPE
    SYNTAX   INTEGER{disabled(0), enabled(1)}
    MAX-ACCESS  read-write
    STATUS   current
    DESCRIPTION "Enabled(1) or Disabled (0)"
    ::= {psRelay1Masks 85}

r1LoadFuses52 OBJECT-TYPE
    SYNTAX   INTEGER{disabled(0), enabled(1)}
    MAX-ACCESS  read-write
    STATUS   current
    DESCRIPTION "Enabled(1) or Disabled (0)"
    ::= {psRelay1Masks 86}

r1UKDVAlarm OBJECT-TYPE
    SYNTAX   INTEGER{disabled(0), enabled(1)}
    MAX-ACCESS  read-write
    STATUS   current
    DESCRIPTION "Enabled(1) or Disabled (0)"
    ::= {psRelay1Masks 87}

--Battery Events in psRelay1Masks
r1BatteryDischarge OBJECT-TYPE
    SYNTAX   INTEGER{disabled(0), enabled(1)}
    MAX-ACCESS  read-write
    STATUS   current
    DESCRIPTION "Enabled(1) or Disabled (0)"
    ::= {psRelay1Masks 96}

r1LowBatteryVoltage OBJECT-TYPE
    SYNTAX   INTEGER{disabled(0), enabled(1)}
    MAX-ACCESS  read-write
    STATUS   current
    DESCRIPTION "Enabled(1) or Disabled (0)"
    ::= {psRelay1Masks 97}

r1BatteryCharge OBJECT-TYPE
    SYNTAX   INTEGER{disabled(0), enabled(1)}
    MAX-ACCESS  read-write
    STATUS   current
    DESCRIPTION "Enabled(1) or Disabled (0)"
    ::= {psRelay1Masks 98}

r1BatteryBoost OBJECT-TYPE
    SYNTAX   INTEGER{disabled(0), enabled(1)}
    MAX-ACCESS  read-write
    STATUS   current
    DESCRIPTION "Enabled(1) or Disabled (0)"
    ::= {psRelay1Masks 99}

r1BatteryFloat OBJECT-TYPE
    SYNTAX   INTEGER{disabled(0), enabled(1)}
    MAX-ACCESS  read-write
    STATUS   current
    DESCRIPTION "Enabled(1) or Disabled (0)"
    ::= {psRelay1Masks 100}

r1BatteryEqualize OBJECT-TYPE
    SYNTAX   INTEGER{disabled(0), enabled(1)}
    MAX-ACCESS  read-write
    STATUS   current
    DESCRIPTION "Enabled(1) or Disabled (0)"
    ::= {psRelay1Masks 101}

r1BatteryTest OBJECT-TYPE
    SYNTAX   INTEGER{disabled(0), enabled(1)}
    MAX-ACCESS  read-write
    STATUS   current
    DESCRIPTION "Enabled(1) or Disabled (0)"
    ::= {psRelay1Masks 102}

r1BatteryFuse1Off OBJECT-TYPE
    SYNTAX   INTEGER{disabled(0), enabled(1)}
    MAX-ACCESS  read-write
    STATUS   current
    DESCRIPTION "Enabled(1) or Disabled (0)"
    ::= {psRelay1Masks 103}

r1BatteryFuse2Off OBJECT-TYPE
    SYNTAX   INTEGER{disabled(0), enabled(1)}
    MAX-ACCESS  read-write
    STATUS   current
    DESCRIPTION "Enabled(1) or Disabled (0)"
    ::= {psRelay1Masks 104}

r1BatteryFuse3Off OBJECT-TYPE
    SYNTAX   INTEGER{disabled(0), enabled(1)}
    MAX-ACCESS  read-write
    STATUS   current
    DESCRIPTION "Enabled(1) or Disabled (0)"
    ::= {psRelay1Masks 105}

r1BatteryFuse4Off OBJECT-TYPE
    SYNTAX   INTEGER{disabled(0), enabled(1)}
    MAX-ACCESS  read-write
    STATUS   current
    DESCRIPTION "Enabled(1) or Disabled (0)"
    ::= {psRelay1Masks 106}

---------------------------------------------------

r1BatteryBlockElGr1Alarm OBJECT-TYPE
    SYNTAX   INTEGER{disabled(0), enabled(1)}
    MAX-ACCESS  read-write
    STATUS   current
    DESCRIPTION "Enabled(1) or Disabled (0)"
    ::= {psRelay1Masks 111}

r1BatteryBlockElGr2Alarm OBJECT-TYPE
    SYNTAX   INTEGER{disabled(0), enabled(1)}
    MAX-ACCESS  read-write
    STATUS   current
    DESCRIPTION "Enabled(1) or Disabled (0)"
    ::= {psRelay1Masks 112}

r1BatteryBlockElGr3Alarm OBJECT-TYPE
    SYNTAX   INTEGER{disabled(0), enabled(1)}
    MAX-ACCESS  read-write
    STATUS   current
    DESCRIPTION "Enabled(1) or Disabled (0)"
    ::= {psRelay1Masks 113}

r1BatteryBlockElGr4Alarm OBJECT-TYPE
    SYNTAX   INTEGER{disabled(0), enabled(1)}
    MAX-ACCESS  read-write
    STATUS   current
    DESCRIPTION "Enabled(1) or Disabled (0)"
    ::= {psRelay1Masks 114}
----------------------------------------------------

r1UPKBAlarm OBJECT-TYPE
    SYNTAX   INTEGER{disabled(0), enabled(1)}
    MAX-ACCESS  read-write
    STATUS   current
    DESCRIPTION "Enabled(1) or Disabled (0)"
    ::= {psRelay1Masks 119}

r1ChargeCurrentLess1A OBJECT-TYPE
    SYNTAX   INTEGER{disabled(0), enabled(1)}
    MAX-ACCESS  read-write
    STATUS   current
    DESCRIPTION "Enabled(1) or Disabled (0)"
    ::= {psRelay1Masks 120}

r1ChargeCurrentLess2A OBJECT-TYPE
    SYNTAX   INTEGER{disabled(0), enabled(1)}
    MAX-ACCESS  read-write
    STATUS   current
    DESCRIPTION "Enabled(1) or Disabled (0)"
    ::= {psRelay1Masks 121}

r1ChargeCurrentLess3A OBJECT-TYPE
    SYNTAX   INTEGER{disabled(0), enabled(1)}
    MAX-ACCESS  read-write
    STATUS   current
    DESCRIPTION "Enabled(1) or Disabled (0)"
    ::= {psRelay1Masks 122}

r1ChargeCurrentLess4A OBJECT-TYPE
    SYNTAX   INTEGER{disabled(0), enabled(1)}
    MAX-ACCESS  read-write
    STATUS   current
    DESCRIPTION "Enabled(1) or Disabled (0)"
    ::= {psRelay1Masks 123}

r1ChargeCurrentLess5A OBJECT-TYPE
    SYNTAX   INTEGER{disabled(0), enabled(1)}
    MAX-ACCESS  read-write
    STATUS   current
    DESCRIPTION "Enabled(1) or Disabled (0)"
    ::= {psRelay1Masks 124}

r1BatteryOverheat OBJECT-TYPE
    SYNTAX   INTEGER{disabled(0), enabled(1)}
    MAX-ACCESS  read-write
    STATUS   current
    DESCRIPTION "Enabled(1) or Disabled (0)"
    ::= {psRelay1Masks 125}

-------------------------------------------------------------------------------------------
-------------------------------------------------------------------------------------------
r1BatteryShortTest OBJECT-TYPE
    SYNTAX   INTEGER{disabled(0), enabled(1)}
    MAX-ACCESS  read-write
    STATUS   current
    DESCRIPTION "Enabled(1) or Disabled (0)"
    ::= {psRelay1Masks 126}

r1BatteryShortTestFail OBJECT-TYPE  
    SYNTAX   INTEGER{disabled(0), enabled(1)}
    MAX-ACCESS  read-write
    STATUS   current
    DESCRIPTION "Enabled(1) or Disabled (0)"
    ::= {psRelay1Masks 127}

-------------------------------------------------------------------------------------------
-------------------------------------------------------------------------------------------

r1BLVDoff OBJECT-TYPE
    SYNTAX   INTEGER{disabled(0), enabled(1)}
    MAX-ACCESS  read-write
    STATUS   current
    DESCRIPTION "Enabled(1) or Disabled (0)"
    ::= {psRelay1Masks 128}

r1LLVD1off OBJECT-TYPE
    SYNTAX   INTEGER{disabled(0), enabled(1)}
    MAX-ACCESS  read-write
    STATUS   current
    DESCRIPTION "Enabled(1) or Disabled (0)"
    ::= {psRelay1Masks 129}

r1LLVD2off OBJECT-TYPE
    SYNTAX   INTEGER{disabled(0), enabled(1)}
    MAX-ACCESS  read-write
    STATUS   current
    DESCRIPTION "Enabled(1) or Disabled (0)"
    ::= {psRelay1Masks 130}

--VBVAlarm in psRelay1Masks
r1VBV1Alarm OBJECT-TYPE
    SYNTAX   INTEGER{disabled(0), enabled(1)}
    MAX-ACCESS  read-write
    STATUS   current
    DESCRIPTION "Alarm of rectifier1 Enabled(1) or Disabled (0)"
    ::= {psRelay1Masks 160}

r1VBV2Alarm OBJECT-TYPE
    SYNTAX   INTEGER{disabled(0), enabled(1)}
    MAX-ACCESS  read-write
    STATUS   current
    DESCRIPTION "Alarm of rectifier2 Enabled(1) or Disabled (0)"
    ::= {psRelay1Masks 161}

r1VBV3Alarm OBJECT-TYPE
    SYNTAX   INTEGER{disabled(0), enabled(1)}
    MAX-ACCESS  read-write
    STATUS   current
    DESCRIPTION "Alarm of rectifier3 Enabled(1) or Disabled (0)"
    ::= {psRelay1Masks 162}

r1VBV4Alarm OBJECT-TYPE
    SYNTAX   INTEGER{disabled(0), enabled(1)}
    MAX-ACCESS  read-write
    STATUS   current
    DESCRIPTION "Alarm of rectifier4 Enabled(1) or Disabled (0)"
    ::= {psRelay1Masks 163}

r1VBV5Alarm OBJECT-TYPE
    SYNTAX   INTEGER{disabled(0), enabled(1)}
    MAX-ACCESS  read-write
    STATUS   current
    DESCRIPTION "Alarm of rectifier5 Enabled(1) or Disabled (0)"
    ::= {psRelay1Masks 164}

r1VBV6Alarm OBJECT-TYPE
    SYNTAX   INTEGER{disabled(0), enabled(1)}
    MAX-ACCESS  read-write
    STATUS   current
    DESCRIPTION "Alarm of rectifier6 Enabled(1) or Disabled (0)"
    ::= {psRelay1Masks 165}

r1VBV7Alarm OBJECT-TYPE
    SYNTAX   INTEGER{disabled(0), enabled(1)}
    MAX-ACCESS  read-write
    STATUS   current
    DESCRIPTION "Alarm of rectifier7 Enabled(1) or Disabled (0)"
    ::= {psRelay1Masks 166}

r1VBV8Alarm OBJECT-TYPE
    SYNTAX   INTEGER{disabled(0), enabled(1)}
    MAX-ACCESS  read-write
    STATUS   current
    DESCRIPTION "Alarm of rectifier8 Enabled(1) or Disabled (0)"
    ::= {psRelay1Masks 167}

r1VBV9Alarm OBJECT-TYPE
    SYNTAX   INTEGER{disabled(0), enabled(1)}
    MAX-ACCESS  read-write
    STATUS   current
    DESCRIPTION "Alarm of rectifier9 Enabled(1) or Disabled (0)"
    ::= {psRelay1Masks 168}

r1VBV10Alarm OBJECT-TYPE
    SYNTAX   INTEGER{disabled(0), enabled(1)}
    MAX-ACCESS  read-write
    STATUS   current
    DESCRIPTION "Alarm of rectifier10 Enabled(1) or Disabled (0)"
    ::= {psRelay1Masks 169}

r1VBV11Alarm OBJECT-TYPE
    SYNTAX   INTEGER{disabled(0), enabled(1)}
    MAX-ACCESS  read-write
    STATUS   current
    DESCRIPTION "Alarm of rectifier11 Enabled(1) or Disabled (0)"
    ::= {psRelay1Masks 170}

r1VBV12Alarm OBJECT-TYPE
    SYNTAX   INTEGER{disabled(0), enabled(1)}
    MAX-ACCESS  read-write
    STATUS   current
    DESCRIPTION "Alarm of rectifier12 Enabled(1) or Disabled (0)"
    ::= {psRelay1Masks 171}

r1VBV13Alarm OBJECT-TYPE
    SYNTAX   INTEGER{disabled(0), enabled(1)}
    MAX-ACCESS  read-write
    STATUS   current
    DESCRIPTION "Alarm of rectifier13 Enabled(1) or Disabled (0)"
    ::= {psRelay1Masks 172}

r1VBV14Alarm OBJECT-TYPE
    SYNTAX   INTEGER{disabled(0), enabled(1)}
    MAX-ACCESS  read-write
    STATUS   current
    DESCRIPTION "Alarm of rectifier14 Enabled(1) or Disabled (0)"
    ::= {psRelay1Masks 173}

r1VBV15Alarm OBJECT-TYPE
    SYNTAX   INTEGER{disabled(0), enabled(1)}
    MAX-ACCESS  read-write
    STATUS   current
    DESCRIPTION "Alarm of rectifier15 Enabled(1) or Disabled (0)"
    ::= {psRelay1Masks 174}

r1VBV16Alarm OBJECT-TYPE
    SYNTAX   INTEGER{disabled(0), enabled(1)}
    MAX-ACCESS  read-write
    STATUS   current
    DESCRIPTION "Alarm of rectifier16 Enabled(1) or Disabled (0)"
    ::= {psRelay1Masks 175}

r1VBV17Alarm OBJECT-TYPE
    SYNTAX   INTEGER{disabled(0), enabled(1)}
    MAX-ACCESS  read-write
    STATUS   current
    DESCRIPTION "Alarm of rectifier17 Enabled(1) or Disabled (0)"
    ::= {psRelay1Masks 176}

r1VBV18Alarm OBJECT-TYPE
    SYNTAX   INTEGER{disabled(0), enabled(1)}
    MAX-ACCESS  read-write
    STATUS   current
    DESCRIPTION "Alarm of rectifier18 Enabled(1) or Disabled (0)"
    ::= {psRelay1Masks 177}

r1VBV19Alarm OBJECT-TYPE
    SYNTAX   INTEGER{disabled(0), enabled(1)}
    MAX-ACCESS  read-write
    STATUS   current
    DESCRIPTION "Alarm of rectifier19 Enabled(1) or Disabled (0)"
    ::= {psRelay1Masks 178}

r1VBV20Alarm OBJECT-TYPE
    SYNTAX   INTEGER{disabled(0), enabled(1)}
    MAX-ACCESS  read-write
    STATUS   current
    DESCRIPTION "Alarm of rectifier20 Enabled(1) or Disabled (0)"
    ::= {psRelay1Masks 179}

r1VBV21Alarm OBJECT-TYPE
    SYNTAX   INTEGER{disabled(0), enabled(1)}
    MAX-ACCESS  read-write
    STATUS   current
    DESCRIPTION "Alarm of rectifier21 Enabled(1) or Disabled (0)"
    ::= {psRelay1Masks 180}

r1VBV22Alarm OBJECT-TYPE
    SYNTAX   INTEGER{disabled(0), enabled(1)}
    MAX-ACCESS  read-write
    STATUS   current
    DESCRIPTION "Alarm of rectifier22 Enabled(1) or Disabled (0)"
    ::= {psRelay1Masks 181}

r1VBV23Alarm OBJECT-TYPE
    SYNTAX   INTEGER{disabled(0), enabled(1)}
    MAX-ACCESS  read-write
    STATUS   current
    DESCRIPTION "Alarm of rectifier23 Enabled(1) or Disabled (0)"
    ::= {psRelay1Masks 182}

r1VBV24Alarm OBJECT-TYPE
    SYNTAX   INTEGER{disabled(0), enabled(1)}
    MAX-ACCESS  read-write
    STATUS   current
    DESCRIPTION "Alarm of rectifier24 Enabled(1) or Disabled (0)"
    ::= {psRelay1Masks 183}

r1VBV25Alarm OBJECT-TYPE
    SYNTAX   INTEGER{disabled(0), enabled(1)}
    MAX-ACCESS  read-write
    STATUS   current
    DESCRIPTION "Alarm of rectifier25 Enabled(1) or Disabled (0)"
    ::= {psRelay1Masks 184}

r1VBV26Alarm OBJECT-TYPE
    SYNTAX   INTEGER{disabled(0), enabled(1)}
    MAX-ACCESS  read-write
    STATUS   current
    DESCRIPTION "Alarm of rectifier26 Enabled(1) or Disabled (0)"
    ::= {psRelay1Masks 185}

r1VBV27Alarm OBJECT-TYPE
    SYNTAX   INTEGER{disabled(0), enabled(1)}
    MAX-ACCESS  read-write
    STATUS   current
    DESCRIPTION "Alarm of rectifier27 Enabled(1) or Disabled (0)"
    ::= {psRelay1Masks 186}

r1VBV28Alarm OBJECT-TYPE
    SYNTAX   INTEGER{disabled(0), enabled(1)}
    MAX-ACCESS  read-write
    STATUS   current
    DESCRIPTION "Alarm of rectifier28 Enabled(1) or Disabled (0)"
    ::= {psRelay1Masks 187}

r1VBV29Alarm OBJECT-TYPE
    SYNTAX   INTEGER{disabled(0), enabled(1)}
    MAX-ACCESS  read-write
    STATUS   current
    DESCRIPTION "Alarm of rectifier29 Enabled(1) or Disabled (0)"
    ::= {psRelay1Masks 188}

r1VBV30Alarm OBJECT-TYPE
    SYNTAX   INTEGER{disabled(0), enabled(1)}
    MAX-ACCESS  read-write
    STATUS   current
    DESCRIPTION "Alarm of rectifier30 Enabled(1) or Disabled (0)"
    ::= {psRelay1Masks 189}

r1VBV31Alarm OBJECT-TYPE
    SYNTAX   INTEGER{disabled(0), enabled(1)}
    MAX-ACCESS  read-write
    STATUS   current
    DESCRIPTION "Alarm of rectifier31 Enabled(1) or Disabled (0)"
    ::= {psRelay1Masks 190}

r1VBV32Alarm OBJECT-TYPE
    SYNTAX   INTEGER{disabled(0), enabled(1)}
    MAX-ACCESS  read-write
    STATUS   current
    DESCRIPTION "Alarm of rectifier32 Enabled(1) or Disabled (0)"
    ::= {psRelay1Masks 191}

r1VBV33Alarm OBJECT-TYPE
    SYNTAX   INTEGER{disabled(0), enabled(1)}
    MAX-ACCESS  read-write
    STATUS   current
    DESCRIPTION "Alarm of rectifier33 Enabled(1) or Disabled (0)"
    ::= {psRelay1Masks 192}

r1VBV34Alarm OBJECT-TYPE
    SYNTAX   INTEGER{disabled(0), enabled(1)}
    MAX-ACCESS  read-write
    STATUS   current
    DESCRIPTION "Alarm of rectifier34 Enabled(1) or Disabled (0)"
    ::= {psRelay1Masks 193}

r1VBV35Alarm OBJECT-TYPE
    SYNTAX   INTEGER{disabled(0), enabled(1)}
    MAX-ACCESS  read-write
    STATUS   current
    DESCRIPTION "Alarm of rectifier35 Enabled(1) or Disabled (0)"
    ::= {psRelay1Masks 194}

r1VBV36Alarm OBJECT-TYPE
    SYNTAX   INTEGER{disabled(0), enabled(1)}
    MAX-ACCESS  read-write
    STATUS   current
    DESCRIPTION "Alarm of rectifier36 Enabled(1) or Disabled (0)"
    ::= {psRelay1Masks 195}

r1VBV37Alarm OBJECT-TYPE
    SYNTAX   INTEGER{disabled(0), enabled(1)}
    MAX-ACCESS  read-write
    STATUS   current
    DESCRIPTION "Alarm of rectifier37 Enabled(1) or Disabled (0)"
    ::= {psRelay1Masks 196}

r1VBV38Alarm OBJECT-TYPE
    SYNTAX   INTEGER{disabled(0), enabled(1)}
    MAX-ACCESS  read-write
    STATUS   current
    DESCRIPTION "Alarm of rectifier38 Enabled(1) or Disabled (0)"
    ::= {psRelay1Masks 197}

r1VBV39Alarm OBJECT-TYPE
    SYNTAX   INTEGER{disabled(0), enabled(1)}
    MAX-ACCESS  read-write
    STATUS   current
    DESCRIPTION "Alarm of rectifier39 Enabled(1) or Disabled (0)"
    ::= {psRelay1Masks 198}

r1VBV40Alarm OBJECT-TYPE
    SYNTAX   INTEGER{disabled(0), enabled(1)}
    MAX-ACCESS  read-write
    STATUS   current
    DESCRIPTION "Alarm of rectifier40 Enabled(1) or Disabled (0)"
    ::= {psRelay1Masks 199}

r1VBV41Alarm OBJECT-TYPE
    SYNTAX   INTEGER{disabled(0), enabled(1)}
    MAX-ACCESS  read-write
    STATUS   current
    DESCRIPTION "Alarm of rectifier41 Enabled(1) or Disabled (0)"
    ::= {psRelay1Masks 200}

r1VBV42Alarm OBJECT-TYPE
    SYNTAX   INTEGER{disabled(0), enabled(1)}
    MAX-ACCESS  read-write
    STATUS   current
    DESCRIPTION "Alarm of rectifier42 Enabled(1) or Disabled (0)"
    ::= {psRelay1Masks 201}

r1VBV43Alarm OBJECT-TYPE
    SYNTAX   INTEGER{disabled(0), enabled(1)}
    MAX-ACCESS  read-write
    STATUS   current
    DESCRIPTION "Alarm of rectifier43 Enabled(1) or Disabled (0)"
    ::= {psRelay1Masks 202}

r1VBV44Alarm OBJECT-TYPE
    SYNTAX   INTEGER{disabled(0), enabled(1)}
    MAX-ACCESS  read-write
    STATUS   current
    DESCRIPTION "Alarm of rectifier44 Enabled(1) or Disabled (0)"
    ::= {psRelay1Masks 203}

r1VBV45Alarm OBJECT-TYPE
    SYNTAX   INTEGER{disabled(0), enabled(1)}
    MAX-ACCESS  read-write
    STATUS   current
    DESCRIPTION "Alarm of rectifier45 Enabled(1) or Disabled (0)"
    ::= {psRelay1Masks 204}

r1VBV46Alarm OBJECT-TYPE
    SYNTAX   INTEGER{disabled(0), enabled(1)}
    MAX-ACCESS  read-write
    STATUS   current
    DESCRIPTION "Alarm of rectifier46 Enabled(1) or Disabled (0)"
    ::= {psRelay1Masks 205}

r1VBV47Alarm OBJECT-TYPE
    SYNTAX   INTEGER{disabled(0), enabled(1)}
    MAX-ACCESS  read-write
    STATUS   current
    DESCRIPTION "Alarm of rectifier47 Enabled(1) or Disabled (0)"
    ::= {psRelay1Masks 206}

r1VBV48Alarm OBJECT-TYPE
    SYNTAX   INTEGER{disabled(0), enabled(1)}
    MAX-ACCESS  read-write
    STATUS   current
    DESCRIPTION "Alarm of rectifier48 Enabled(1) or Disabled (0)"
    ::= {psRelay1Masks 207}

r1VBV49Alarm OBJECT-TYPE
    SYNTAX   INTEGER{disabled(0), enabled(1)}
    MAX-ACCESS  read-write
    STATUS   current
    DESCRIPTION "Alarm of rectifier49 Enabled(1) or Disabled (0)"
    ::= {psRelay1Masks 208}

r1VBV50Alarm OBJECT-TYPE
    SYNTAX   INTEGER{disabled(0), enabled(1)}
    MAX-ACCESS  read-write
    STATUS   current
    DESCRIPTION "Alarm of rectifier50 Enabled(1) or Disabled (0)"
    ::= {psRelay1Masks 209}

r1VBV51Alarm OBJECT-TYPE
    SYNTAX   INTEGER{disabled(0), enabled(1)}
    MAX-ACCESS  read-write
    STATUS   current
    DESCRIPTION "Alarm of rectifier51 Enabled(1) or Disabled (0)"
    ::= {psRelay1Masks 210}

r1VBV52Alarm OBJECT-TYPE
    SYNTAX   INTEGER{disabled(0), enabled(1)}
    MAX-ACCESS  read-write
    STATUS   current
    DESCRIPTION "Alarm of rectifier52 Enabled(1) or Disabled (0)"
    ::= {psRelay1Masks 211}

r1VBV53Alarm OBJECT-TYPE
    SYNTAX   INTEGER{disabled(0), enabled(1)}
    MAX-ACCESS  read-write
    STATUS   current
    DESCRIPTION "Alarm of rectifier53 Enabled(1) or Disabled (0)"
    ::= {psRelay1Masks 212}

r1VBV54Alarm OBJECT-TYPE
    SYNTAX   INTEGER{disabled(0), enabled(1)}
    MAX-ACCESS  read-write
    STATUS   current
    DESCRIPTION "Alarm of rectifier54 Enabled(1) or Disabled (0)"
    ::= {psRelay1Masks 213}

r1VBV55Alarm OBJECT-TYPE
    SYNTAX   INTEGER{disabled(0), enabled(1)}
    MAX-ACCESS  read-write
    STATUS   current
    DESCRIPTION "Alarm of rectifier55 Enabled(1) or Disabled (0)"
    ::= {psRelay1Masks 214}

r1VBV56Alarm OBJECT-TYPE
    SYNTAX   INTEGER{disabled(0), enabled(1)}
    MAX-ACCESS  read-write
    STATUS   current
    DESCRIPTION "Alarm of rectifier56 Enabled(1) or Disabled (0)"
    ::= {psRelay1Masks 215}

r1VBV57Alarm OBJECT-TYPE
    SYNTAX   INTEGER{disabled(0), enabled(1)}
    MAX-ACCESS  read-write
    STATUS   current
    DESCRIPTION "Alarm of rectifier57 Enabled(1) or Disabled (0)"
    ::= {psRelay1Masks 216}

r1VBV58Alarm OBJECT-TYPE
    SYNTAX   INTEGER{disabled(0), enabled(1)}
    MAX-ACCESS  read-write
    STATUS   current
    DESCRIPTION "Alarm of rectifier58 Enabled(1) or Disabled (0)"
    ::= {psRelay1Masks 217}

r1VBV59Alarm OBJECT-TYPE
    SYNTAX   INTEGER{disabled(0), enabled(1)}
    MAX-ACCESS  read-write
    STATUS   current
    DESCRIPTION "Alarm of rectifier59 Enabled(1) or Disabled (0)"
    ::= {psRelay1Masks 218}

r1VBV60Alarm OBJECT-TYPE
    SYNTAX   INTEGER{disabled(0), enabled(1)}
    MAX-ACCESS  read-write
    STATUS   current
    DESCRIPTION "Alarm of rectifier60 Enabled(1) or Disabled (0)"
    ::= {psRelay1Masks 219}

r1VBV61Alarm OBJECT-TYPE
    SYNTAX   INTEGER{disabled(0), enabled(1)}
    MAX-ACCESS  read-write
    STATUS   current
    DESCRIPTION "Alarm of rectifier61 Enabled(1) or Disabled (0)"
    ::= {psRelay1Masks 220}

r1VBV62Alarm OBJECT-TYPE
    SYNTAX   INTEGER{disabled(0), enabled(1)}
    MAX-ACCESS  read-write
    STATUS   current
    DESCRIPTION "Alarm of rectifier62 Enabled(1) or Disabled (0)"
    ::= {psRelay1Masks 221}

r1VBV63Alarm OBJECT-TYPE
    SYNTAX   INTEGER{disabled(0), enabled(1)}
    MAX-ACCESS  read-write
    STATUS   current
    DESCRIPTION "Alarm of rectifier63 Enabled(1) or Disabled (0)"
    ::= {psRelay1Masks 222}

r1VBV64Alarm OBJECT-TYPE
    SYNTAX   INTEGER{disabled(0), enabled(1)}
    MAX-ACCESS  read-write
    STATUS   current
    DESCRIPTION "Alarm of rectifier64 Enabled(1) or Disabled (0)"
    ::= {psRelay1Masks 223}

r1VBV65Alarm OBJECT-TYPE
    SYNTAX   INTEGER{disabled(0), enabled(1)}
    MAX-ACCESS  read-write
    STATUS   current
    DESCRIPTION "Alarm of rectifier65 Enabled(1) or Disabled (0)"
    ::= {psRelay1Masks 224}

r1VBV66Alarm OBJECT-TYPE
    SYNTAX   INTEGER{disabled(0), enabled(1)}
    MAX-ACCESS  read-write
    STATUS   current
    DESCRIPTION "Alarm of rectifier66 Enabled(1) or Disabled (0)"
    ::= {psRelay1Masks 225}

r1VBV67Alarm OBJECT-TYPE
    SYNTAX   INTEGER{disabled(0), enabled(1)}
    MAX-ACCESS  read-write
    STATUS   current
    DESCRIPTION "Alarm of rectifier67 Enabled(1) or Disabled (0)"
    ::= {psRelay1Masks 226}

r1VBV68Alarm OBJECT-TYPE
    SYNTAX   INTEGER{disabled(0), enabled(1)}
    MAX-ACCESS  read-write
    STATUS   current
    DESCRIPTION "Alarm of rectifier68 Enabled(1) or Disabled (0)"
    ::= {psRelay1Masks 227}

r1VBV69Alarm OBJECT-TYPE
    SYNTAX   INTEGER{disabled(0), enabled(1)}
    MAX-ACCESS  read-write
    STATUS   current
    DESCRIPTION "Alarm of rectifier69 Enabled(1) or Disabled (0)"
    ::= {psRelay1Masks 228}

r1VBV70Alarm OBJECT-TYPE
    SYNTAX   INTEGER{disabled(0), enabled(1)}
    MAX-ACCESS  read-write
    STATUS   current
    DESCRIPTION "Alarm of rectifier70 Enabled(1) or Disabled (0)"
    ::= {psRelay1Masks 229}

r1VBV71Alarm OBJECT-TYPE
    SYNTAX   INTEGER{disabled(0), enabled(1)}
    MAX-ACCESS  read-write
    STATUS   current
    DESCRIPTION "Alarm of rectifier71 Enabled(1) or Disabled (0)"
    ::= {psRelay1Masks 230}

r1VBV72Alarm OBJECT-TYPE
    SYNTAX   INTEGER{disabled(0), enabled(1)}
    MAX-ACCESS  read-write
    STATUS   current
    DESCRIPTION "Alarm of rectifier72 Enabled(1) or Disabled (0)"
    ::= {psRelay1Masks 231}

r1VBV73Alarm OBJECT-TYPE
    SYNTAX   INTEGER{disabled(0), enabled(1)}
    MAX-ACCESS  read-write
    STATUS   current
    DESCRIPTION "Alarm of rectifier73 Enabled(1) or Disabled (0)"
    ::= {psRelay1Masks 232}

r1VBV74Alarm OBJECT-TYPE
    SYNTAX   INTEGER{disabled(0), enabled(1)}
    MAX-ACCESS  read-write
    STATUS   current
    DESCRIPTION "Alarm of rectifier74 Enabled(1) or Disabled (0)"
    ::= {psRelay1Masks 233}

r1VBV75Alarm OBJECT-TYPE
    SYNTAX   INTEGER{disabled(0), enabled(1)}
    MAX-ACCESS  read-write
    STATUS   current
    DESCRIPTION "Alarm of rectifier75 Enabled(1) or Disabled (0)"
    ::= {psRelay1Masks 234}

r1VBV76Alarm OBJECT-TYPE
    SYNTAX   INTEGER{disabled(0), enabled(1)}
    MAX-ACCESS  read-write
    STATUS   current
    DESCRIPTION "Alarm of rectifier76 Enabled(1) or Disabled (0)"
    ::= {psRelay1Masks 235}

r1VBV77Alarm OBJECT-TYPE
    SYNTAX   INTEGER{disabled(0), enabled(1)}
    MAX-ACCESS  read-write
    STATUS   current
    DESCRIPTION "Alarm of rectifier77 Enabled(1) or Disabled (0)"
    ::= {psRelay1Masks 236}

r1VBV78Alarm OBJECT-TYPE
    SYNTAX   INTEGER{disabled(0), enabled(1)}
    MAX-ACCESS  read-write
    STATUS   current
    DESCRIPTION "Alarm of rectifier78 Enabled(1) or Disabled (0)"
    ::= {psRelay1Masks 237}

r1VBV79Alarm OBJECT-TYPE
    SYNTAX   INTEGER{disabled(0), enabled(1)}
    MAX-ACCESS  read-write
    STATUS   current
    DESCRIPTION "Alarm of rectifier79 Enabled(1) or Disabled (0)"
    ::= {psRelay1Masks 238}

r1VBV80Alarm OBJECT-TYPE
    SYNTAX   INTEGER{disabled(0), enabled(1)}
    MAX-ACCESS  read-write
    STATUS   current
    DESCRIPTION "Alarm of rectifier80 Enabled(1) or Disabled (0)"
    ::= {psRelay1Masks 239}

r1VBV81Alarm OBJECT-TYPE
    SYNTAX   INTEGER{disabled(0), enabled(1)}
    MAX-ACCESS  read-write
    STATUS   current
    DESCRIPTION "Alarm of rectifier81 Enabled(1) or Disabled (0)"
    ::= {psRelay1Masks 240}

r1VBV82Alarm OBJECT-TYPE
    SYNTAX   INTEGER{disabled(0), enabled(1)}
    MAX-ACCESS  read-write
    STATUS   current
    DESCRIPTION "Alarm of rectifier82 Enabled(1) or Disabled (0)"
    ::= {psRelay1Masks 241}

r1VBV83Alarm OBJECT-TYPE
    SYNTAX   INTEGER{disabled(0), enabled(1)}
    MAX-ACCESS  read-write
    STATUS   current
    DESCRIPTION "Alarm of rectifier83 Enabled(1) or Disabled (0)"
    ::= {psRelay1Masks 242}

r1VBV84Alarm OBJECT-TYPE
    SYNTAX   INTEGER{disabled(0), enabled(1)}
    MAX-ACCESS  read-write
    STATUS   current
    DESCRIPTION "Alarm of rectifier84 Enabled(1) or Disabled (0)"
    ::= {psRelay1Masks 243}

r1VBV85Alarm OBJECT-TYPE
    SYNTAX   INTEGER{disabled(0), enabled(1)}
    MAX-ACCESS  read-write
    STATUS   current
    DESCRIPTION "Alarm of rectifier85 Enabled(1) or Disabled (0)"
    ::= {psRelay1Masks 244}

r1VBV86Alarm OBJECT-TYPE
    SYNTAX   INTEGER{disabled(0), enabled(1)}
    MAX-ACCESS  read-write
    STATUS   current
    DESCRIPTION "Alarm of rectifier86 Enabled(1) or Disabled (0)"
    ::= {psRelay1Masks 245}

r1VBV87Alarm OBJECT-TYPE
    SYNTAX   INTEGER{disabled(0), enabled(1)}
    MAX-ACCESS  read-write
    STATUS   current
    DESCRIPTION "Alarm of rectifier87 Enabled(1) or Disabled (0)"
    ::= {psRelay1Masks 246}

r1VBV88Alarm OBJECT-TYPE
    SYNTAX   INTEGER{disabled(0), enabled(1)}
    MAX-ACCESS  read-write
    STATUS   current
    DESCRIPTION "Alarm of rectifier88 Enabled(1) or Disabled (0)"
    ::= {psRelay1Masks 247}

r1VBV89Alarm OBJECT-TYPE
    SYNTAX   INTEGER{disabled(0), enabled(1)}
    MAX-ACCESS  read-write
    STATUS   current
    DESCRIPTION "Alarm of rectifier89 Enabled(1) or Disabled (0)"
    ::= {psRelay1Masks 248}

r1VBV90Alarm OBJECT-TYPE
    SYNTAX   INTEGER{disabled(0), enabled(1)}
    MAX-ACCESS  read-write
    STATUS   current
    DESCRIPTION "Alarm of rectifier90 Enabled(1) or Disabled (0)"
    ::= {psRelay1Masks 249}

r1VBV91Alarm OBJECT-TYPE
    SYNTAX   INTEGER{disabled(0), enabled(1)}
    MAX-ACCESS  read-write
    STATUS   current
    DESCRIPTION "Alarm of rectifier91 Enabled(1) or Disabled (0)"
    ::= {psRelay1Masks 250}

r1VBV92Alarm OBJECT-TYPE
    SYNTAX   INTEGER{disabled(0), enabled(1)}
    MAX-ACCESS  read-write
    STATUS   current
    DESCRIPTION "Alarm of rectifier92 Enabled(1) or Disabled (0)"
    ::= {psRelay1Masks 251}

r1VBV93Alarm OBJECT-TYPE
    SYNTAX   INTEGER{disabled(0), enabled(1)}
    MAX-ACCESS  read-write
    STATUS   current
    DESCRIPTION "Alarm of rectifier93 Enabled(1) or Disabled (0)"
    ::= {psRelay1Masks 252}

r1VBV94Alarm OBJECT-TYPE
    SYNTAX   INTEGER{disabled(0), enabled(1)}
    MAX-ACCESS  read-write
    STATUS   current
    DESCRIPTION "Alarm of rectifier94 Enabled(1) or Disabled (0)"
    ::= {psRelay1Masks 253}

r1VBV95Alarm OBJECT-TYPE
    SYNTAX   INTEGER{disabled(0), enabled(1)}
    MAX-ACCESS  read-write
    STATUS   current
    DESCRIPTION "Alarm of rectifier95 Enabled(1) or Disabled (0)"
    ::= {psRelay1Masks 254}

r1VBV96Alarm OBJECT-TYPE
    SYNTAX   INTEGER{disabled(0), enabled(1)}
    MAX-ACCESS  read-write
    STATUS   current
    DESCRIPTION "Alarm of rectifier96 Enabled(1) or Disabled (0)"
    ::= {psRelay1Masks 255}

r1VBV97Alarm OBJECT-TYPE
    SYNTAX   INTEGER{disabled(0), enabled(1)}
    MAX-ACCESS  read-write
    STATUS   current
    DESCRIPTION "Alarm of rectifier97 Enabled(1) or Disabled (0)"
    ::= {psRelay1Masks 256}

r1VBV98Alarm OBJECT-TYPE
    SYNTAX   INTEGER{disabled(0), enabled(1)}
    MAX-ACCESS  read-write
    STATUS   current
    DESCRIPTION "Alarm of rectifier98 Enabled(1) or Disabled (0)"
    ::= {psRelay1Masks 257}

r1VBV99Alarm OBJECT-TYPE
    SYNTAX   INTEGER{disabled(0), enabled(1)}
    MAX-ACCESS  read-write
    STATUS   current
    DESCRIPTION "Alarm of rectifier99 Enabled(1) or Disabled (0)"
    ::= {psRelay1Masks 258}

r1VBV100Alarm OBJECT-TYPE
    SYNTAX   INTEGER{disabled(0), enabled(1)}
    MAX-ACCESS  read-write
    STATUS   current
    DESCRIPTION "Alarm of rectifier100 Enabled(1) or Disabled (0)"
    ::= {psRelay1Masks 259}

r1VBV101Alarm OBJECT-TYPE
    SYNTAX   INTEGER{disabled(0), enabled(1)}
    MAX-ACCESS  read-write
    STATUS   current
    DESCRIPTION "Alarm of rectifier101 Enabled(1) or Disabled (0)"
    ::= {psRelay1Masks 260}

r1VBV102Alarm OBJECT-TYPE
    SYNTAX   INTEGER{disabled(0), enabled(1)}
    MAX-ACCESS  read-write
    STATUS   current
    DESCRIPTION "Alarm of rectifier102 Enabled(1) or Disabled (0)"
    ::= {psRelay1Masks 261}

r1VBV103Alarm OBJECT-TYPE
    SYNTAX   INTEGER{disabled(0), enabled(1)}
    MAX-ACCESS  read-write
    STATUS   current
    DESCRIPTION "Alarm of rectifier103 Enabled(1) or Disabled (0)"
    ::= {psRelay1Masks 262}

r1VBV104Alarm OBJECT-TYPE
    SYNTAX   INTEGER{disabled(0), enabled(1)}
    MAX-ACCESS  read-write
    STATUS   current
    DESCRIPTION "Alarm of rectifier104 Enabled(1) or Disabled (0)"
    ::= {psRelay1Masks 263}

r1VBV105Alarm OBJECT-TYPE
    SYNTAX   INTEGER{disabled(0), enabled(1)}
    MAX-ACCESS  read-write
    STATUS   current
    DESCRIPTION "Alarm of rectifier105 Enabled(1) or Disabled (0)"
    ::= {psRelay1Masks 264}

r1VBV106Alarm OBJECT-TYPE
    SYNTAX   INTEGER{disabled(0), enabled(1)}
    MAX-ACCESS  read-write
    STATUS   current
    DESCRIPTION "Alarm of rectifier106 Enabled(1) or Disabled (0)"
    ::= {psRelay1Masks 265}

r1VBV107Alarm OBJECT-TYPE
    SYNTAX   INTEGER{disabled(0), enabled(1)}
    MAX-ACCESS  read-write
    STATUS   current
    DESCRIPTION "Alarm of rectifier107 Enabled(1) or Disabled (0)"
    ::= {psRelay1Masks 266}

r1VBV108Alarm OBJECT-TYPE
    SYNTAX   INTEGER{disabled(0), enabled(1)}
    MAX-ACCESS  read-write
    STATUS   current
    DESCRIPTION "Alarm of rectifier108 Enabled(1) or Disabled (0)"
    ::= {psRelay1Masks 267}

r1VBV109Alarm OBJECT-TYPE
    SYNTAX   INTEGER{disabled(0), enabled(1)}
    MAX-ACCESS  read-write
    STATUS   current
    DESCRIPTION "Alarm of rectifier109 Enabled(1) or Disabled (0)"
    ::= {psRelay1Masks 268}

r1VBV110Alarm OBJECT-TYPE
    SYNTAX   INTEGER{disabled(0), enabled(1)}
    MAX-ACCESS  read-write
    STATUS   current
    DESCRIPTION "Alarm of rectifier110 Enabled(1) or Disabled (0)"
    ::= {psRelay1Masks 269}

r1VBV111Alarm OBJECT-TYPE
    SYNTAX   INTEGER{disabled(0), enabled(1)}
    MAX-ACCESS  read-write
    STATUS   current
    DESCRIPTION "Alarm of rectifier111 Enabled(1) or Disabled (0)"
    ::= {psRelay1Masks 270}

r1VBV112Alarm OBJECT-TYPE
    SYNTAX   INTEGER{disabled(0), enabled(1)}
    MAX-ACCESS  read-write
    STATUS   current
    DESCRIPTION "Alarm of rectifier112 Enabled(1) or Disabled (0)"
    ::= {psRelay1Masks 271}

r1VBV113Alarm OBJECT-TYPE
    SYNTAX   INTEGER{disabled(0), enabled(1)}
    MAX-ACCESS  read-write
    STATUS   current
    DESCRIPTION "Alarm of rectifier113 Enabled(1) or Disabled (0)"
    ::= {psRelay1Masks 272}

r1VBV114Alarm OBJECT-TYPE
    SYNTAX   INTEGER{disabled(0), enabled(1)}
    MAX-ACCESS  read-write
    STATUS   current
    DESCRIPTION "Alarm of rectifier114 Enabled(1) or Disabled (0)"
    ::= {psRelay1Masks 273}

r1VBV115Alarm OBJECT-TYPE
    SYNTAX   INTEGER{disabled(0), enabled(1)}
    MAX-ACCESS  read-write
    STATUS   current
    DESCRIPTION "Alarm of rectifier115 Enabled(1) or Disabled (0)"
    ::= {psRelay1Masks 274}

r1VBV116Alarm OBJECT-TYPE
    SYNTAX   INTEGER{disabled(0), enabled(1)}
    MAX-ACCESS  read-write
    STATUS   current
    DESCRIPTION "Alarm of rectifier116 Enabled(1) or Disabled (0)"
    ::= {psRelay1Masks 275}

r1VBV117Alarm OBJECT-TYPE
    SYNTAX   INTEGER{disabled(0), enabled(1)}
    MAX-ACCESS  read-write
    STATUS   current
    DESCRIPTION "Alarm of rectifier117 Enabled(1) or Disabled (0)"
    ::= {psRelay1Masks 276}

r1VBV118Alarm OBJECT-TYPE
    SYNTAX   INTEGER{disabled(0), enabled(1)}
    MAX-ACCESS  read-write
    STATUS   current
    DESCRIPTION "Alarm of rectifier118 Enabled(1) or Disabled (0)"
    ::= {psRelay1Masks 277}

r1VBV119Alarm OBJECT-TYPE
    SYNTAX   INTEGER{disabled(0), enabled(1)}
    MAX-ACCESS  read-write
    STATUS   current
    DESCRIPTION "Alarm of rectifier119 Enabled(1) or Disabled (0)"
    ::= {psRelay1Masks 278}

r1VBV120Alarm OBJECT-TYPE
    SYNTAX   INTEGER{disabled(0), enabled(1)}
    MAX-ACCESS  read-write
    STATUS   current
    DESCRIPTION "Alarm of rectifier120 Enabled(1) or Disabled (0)"
    ::= {psRelay1Masks 279}

r1VBV121Alarm OBJECT-TYPE
    SYNTAX   INTEGER{disabled(0), enabled(1)}
    MAX-ACCESS  read-write
    STATUS   current
    DESCRIPTION "Alarm of rectifier121 Enabled(1) or Disabled (0)"
    ::= {psRelay1Masks 280}

r1VBV122Alarm OBJECT-TYPE
    SYNTAX   INTEGER{disabled(0), enabled(1)}
    MAX-ACCESS  read-write
    STATUS   current
    DESCRIPTION "Alarm of rectifier122 Enabled(1) or Disabled (0)"
    ::= {psRelay1Masks 281}

r1VBV123Alarm OBJECT-TYPE
    SYNTAX   INTEGER{disabled(0), enabled(1)}
    MAX-ACCESS  read-write
    STATUS   current
    DESCRIPTION "Alarm of rectifier123 Enabled(1) or Disabled (0)"
    ::= {psRelay1Masks 282}

r1VBV124Alarm OBJECT-TYPE
    SYNTAX   INTEGER{disabled(0), enabled(1)}
    MAX-ACCESS  read-write
    STATUS   current
    DESCRIPTION "Alarm of rectifier124 Enabled(1) or Disabled (0)"
    ::= {psRelay1Masks 283}

r1VBV125Alarm OBJECT-TYPE
    SYNTAX   INTEGER{disabled(0), enabled(1)}
    MAX-ACCESS  read-write
    STATUS   current
    DESCRIPTION "Alarm of rectifier125 Enabled(1) or Disabled (0)"
    ::= {psRelay1Masks 284}

r1VBV126Alarm OBJECT-TYPE
    SYNTAX   INTEGER{disabled(0), enabled(1)}
    MAX-ACCESS  read-write
    STATUS   current
    DESCRIPTION "Alarm of rectifier126 Enabled(1) or Disabled (0)"
    ::= {psRelay1Masks 285}

r1VBV127Alarm OBJECT-TYPE
    SYNTAX   INTEGER{disabled(0), enabled(1)}
    MAX-ACCESS  read-write
    STATUS   current
    DESCRIPTION "Alarm of rectifier127 Enabled(1) or Disabled (0)"
    ::= {psRelay1Masks 286}

r1VBV128Alarm OBJECT-TYPE
    SYNTAX   INTEGER{disabled(0), enabled(1)}
    MAX-ACCESS  read-write
    STATUS   current
    DESCRIPTION "Alarm of rectifier128 Enabled(1) or Disabled (0)"
    ::= {psRelay1Masks 287}

r1VBV129Alarm OBJECT-TYPE
    SYNTAX   INTEGER{disabled(0), enabled(1)}
    MAX-ACCESS  read-write
    STATUS   current
    DESCRIPTION "Alarm of rectifier129 Enabled(1) or Disabled (0)"
    ::= {psRelay1Masks 288}

r1VBV130Alarm OBJECT-TYPE
    SYNTAX   INTEGER{disabled(0), enabled(1)}
    MAX-ACCESS  read-write
    STATUS   current
    DESCRIPTION "Alarm of rectifier130 Enabled(1) or Disabled (0)"
    ::= {psRelay1Masks 289}

r1VBV131Alarm OBJECT-TYPE
    SYNTAX   INTEGER{disabled(0), enabled(1)}
    MAX-ACCESS  read-write
    STATUS   current
    DESCRIPTION "Alarm of rectifier131 Enabled(1) or Disabled (0)"
    ::= {psRelay1Masks 290}

r1VBV132Alarm OBJECT-TYPE
    SYNTAX   INTEGER{disabled(0), enabled(1)}
    MAX-ACCESS  read-write
    STATUS   current
    DESCRIPTION "Alarm of rectifier132 Enabled(1) or Disabled (0)"
    ::= {psRelay1Masks 291}

r1VBV133Alarm OBJECT-TYPE
    SYNTAX   INTEGER{disabled(0), enabled(1)}
    MAX-ACCESS  read-write
    STATUS   current
    DESCRIPTION "Alarm of rectifier133 Enabled(1) or Disabled (0)"
    ::= {psRelay1Masks 292}

r1VBV134Alarm OBJECT-TYPE
    SYNTAX   INTEGER{disabled(0), enabled(1)}
    MAX-ACCESS  read-write
    STATUS   current
    DESCRIPTION "Alarm of rectifier134 Enabled(1) or Disabled (0)"
    ::= {psRelay1Masks 293}

r1VBV135Alarm OBJECT-TYPE
    SYNTAX   INTEGER{disabled(0), enabled(1)}
    MAX-ACCESS  read-write
    STATUS   current
    DESCRIPTION "Alarm of rectifier135 Enabled(1) or Disabled (0)"
    ::= {psRelay1Masks 294}

r1VBV136Alarm OBJECT-TYPE
    SYNTAX   INTEGER{disabled(0), enabled(1)}
    MAX-ACCESS  read-write
    STATUS   current
    DESCRIPTION "Alarm of rectifier136 Enabled(1) or Disabled (0)"
    ::= {psRelay1Masks 295}

r1VBV137Alarm OBJECT-TYPE
    SYNTAX   INTEGER{disabled(0), enabled(1)}
    MAX-ACCESS  read-write
    STATUS   current
    DESCRIPTION "Alarm of rectifier137 Enabled(1) or Disabled (0)"
    ::= {psRelay1Masks 296}

r1VBV138Alarm OBJECT-TYPE
    SYNTAX   INTEGER{disabled(0), enabled(1)}
    MAX-ACCESS  read-write
    STATUS   current
    DESCRIPTION "Alarm of rectifier138 Enabled(1) or Disabled (0)"
    ::= {psRelay1Masks 297}

r1VBV139Alarm OBJECT-TYPE
    SYNTAX   INTEGER{disabled(0), enabled(1)}
    MAX-ACCESS  read-write
    STATUS   current
    DESCRIPTION "Alarm of rectifier139 Enabled(1) or Disabled (0)"
    ::= {psRelay1Masks 298}

r1VBV140Alarm OBJECT-TYPE
    SYNTAX   INTEGER{disabled(0), enabled(1)}
    MAX-ACCESS  read-write
    STATUS   current
    DESCRIPTION "Alarm of rectifier140 Enabled(1) or Disabled (0)"
    ::= {psRelay1Masks 299}

r1VBV141Alarm OBJECT-TYPE
    SYNTAX   INTEGER{disabled(0), enabled(1)}
    MAX-ACCESS  read-write
    STATUS   current
    DESCRIPTION "Alarm of rectifier141 Enabled(1) or Disabled (0)"
    ::= {psRelay1Masks 300}

r1VBV142Alarm OBJECT-TYPE
    SYNTAX   INTEGER{disabled(0), enabled(1)}
    MAX-ACCESS  read-write
    STATUS   current
    DESCRIPTION "Alarm of rectifier142 Enabled(1) or Disabled (0)"
    ::= {psRelay1Masks 301}

r1VBV143Alarm OBJECT-TYPE
    SYNTAX   INTEGER{disabled(0), enabled(1)}
    MAX-ACCESS  read-write
    STATUS   current
    DESCRIPTION "Alarm of rectifier143 Enabled(1) or Disabled (0)"
    ::= {psRelay1Masks 302}

r1VBV144Alarm OBJECT-TYPE
    SYNTAX   INTEGER{disabled(0), enabled(1)}
    MAX-ACCESS  read-write
    STATUS   current
    DESCRIPTION "Alarm of rectifier144 Enabled(1) or Disabled (0)"
    ::= {psRelay1Masks 303}

r1VBV145Alarm OBJECT-TYPE
    SYNTAX   INTEGER{disabled(0), enabled(1)}
    MAX-ACCESS  read-write
    STATUS   current
    DESCRIPTION "Alarm of rectifier145 Enabled(1) or Disabled (0)"
    ::= {psRelay1Masks 304}

r1VBV146Alarm OBJECT-TYPE
    SYNTAX   INTEGER{disabled(0), enabled(1)}
    MAX-ACCESS  read-write
    STATUS   current
    DESCRIPTION "Alarm of rectifier146 Enabled(1) or Disabled (0)"
    ::= {psRelay1Masks 305}

r1VBV147Alarm OBJECT-TYPE
    SYNTAX   INTEGER{disabled(0), enabled(1)}
    MAX-ACCESS  read-write
    STATUS   current
    DESCRIPTION "Alarm of rectifier147 Enabled(1) or Disabled (0)"
    ::= {psRelay1Masks 306}

r1VBV148Alarm OBJECT-TYPE
    SYNTAX   INTEGER{disabled(0), enabled(1)}
    MAX-ACCESS  read-write
    STATUS   current
    DESCRIPTION "Alarm of rectifier148 Enabled(1) or Disabled (0)"
    ::= {psRelay1Masks 307}

r1VBV149Alarm OBJECT-TYPE
    SYNTAX   INTEGER{disabled(0), enabled(1)}
    MAX-ACCESS  read-write
    STATUS   current
    DESCRIPTION "Alarm of rectifier149 Enabled(1) or Disabled (0)"
    ::= {psRelay1Masks 308}

r1VBV150Alarm OBJECT-TYPE
    SYNTAX   INTEGER{disabled(0), enabled(1)}
    MAX-ACCESS  read-write
    STATUS   current
    DESCRIPTION "Alarm of rectifier150 Enabled(1) or Disabled (0)"
    ::= {psRelay1Masks 309}

r1VBV151Alarm OBJECT-TYPE
    SYNTAX   INTEGER{disabled(0), enabled(1)}
    MAX-ACCESS  read-write
    STATUS   current
    DESCRIPTION "Alarm of rectifier151 Enabled(1) or Disabled (0)"
    ::= {psRelay1Masks 310}

r1VBV152Alarm OBJECT-TYPE
    SYNTAX   INTEGER{disabled(0), enabled(1)}
    MAX-ACCESS  read-write
    STATUS   current
    DESCRIPTION "Alarm of rectifier152 Enabled(1) or Disabled (0)"
    ::= {psRelay1Masks 311}

r1VBV153Alarm OBJECT-TYPE
    SYNTAX   INTEGER{disabled(0), enabled(1)}
    MAX-ACCESS  read-write
    STATUS   current
    DESCRIPTION "Alarm of rectifier153 Enabled(1) or Disabled (0)"
    ::= {psRelay1Masks 312}

r1VBV154Alarm OBJECT-TYPE
    SYNTAX   INTEGER{disabled(0), enabled(1)}
    MAX-ACCESS  read-write
    STATUS   current
    DESCRIPTION "Alarm of rectifier154 Enabled(1) or Disabled (0)"
    ::= {psRelay1Masks 313}

r1VBV155Alarm OBJECT-TYPE
    SYNTAX   INTEGER{disabled(0), enabled(1)}
    MAX-ACCESS  read-write
    STATUS   current
    DESCRIPTION "Alarm of rectifier155 Enabled(1) or Disabled (0)"
    ::= {psRelay1Masks 314}

r1VBV156Alarm OBJECT-TYPE
    SYNTAX   INTEGER{disabled(0), enabled(1)}
    MAX-ACCESS  read-write
    STATUS   current
    DESCRIPTION "Alarm of rectifier156 Enabled(1) or Disabled (0)"
    ::= {psRelay1Masks 315}

r1VBV157Alarm OBJECT-TYPE
    SYNTAX   INTEGER{disabled(0), enabled(1)}
    MAX-ACCESS  read-write
    STATUS   current
    DESCRIPTION "Alarm of rectifier157 Enabled(1) or Disabled (0)"
    ::= {psRelay1Masks 316}

r1VBV158Alarm OBJECT-TYPE
    SYNTAX   INTEGER{disabled(0), enabled(1)}
    MAX-ACCESS  read-write
    STATUS   current
    DESCRIPTION "Alarm of rectifier158 Enabled(1) or Disabled (0)"
    ::= {psRelay1Masks 317}

r1VBV159Alarm OBJECT-TYPE
    SYNTAX   INTEGER{disabled(0), enabled(1)}
    MAX-ACCESS  read-write
    STATUS   current
    DESCRIPTION "Alarm of rectifier159 Enabled(1) or Disabled (0)"
    ::= {psRelay1Masks 318}

r1VBV160Alarm OBJECT-TYPE
    SYNTAX   INTEGER{disabled(0), enabled(1)}
    MAX-ACCESS  read-write
    STATUS   current
    DESCRIPTION "Alarm of rectifier160 Enabled(1) or Disabled (0)"
    ::= {psRelay1Masks 319}

r1VBV161Alarm OBJECT-TYPE
    SYNTAX   INTEGER{disabled(0), enabled(1)}
    MAX-ACCESS  read-write
    STATUS   current
    DESCRIPTION "Alarm of rectifier161 Enabled(1) or Disabled (0)"
    ::= {psRelay1Masks 320}

r1VBV162Alarm OBJECT-TYPE
    SYNTAX   INTEGER{disabled(0), enabled(1)}
    MAX-ACCESS  read-write
    STATUS   current
    DESCRIPTION "Alarm of rectifier162 Enabled(1) or Disabled (0)"
    ::= {psRelay1Masks 321}

r1VBV163Alarm OBJECT-TYPE
    SYNTAX   INTEGER{disabled(0), enabled(1)}
    MAX-ACCESS  read-write
    STATUS   current
    DESCRIPTION "Alarm of rectifier163 Enabled(1) or Disabled (0)"
    ::= {psRelay1Masks 322}

r1VBV164Alarm OBJECT-TYPE
    SYNTAX   INTEGER{disabled(0), enabled(1)}
    MAX-ACCESS  read-write
    STATUS   current
    DESCRIPTION "Alarm of rectifier164 Enabled(1) or Disabled (0)"
    ::= {psRelay1Masks 323}

r1VBV165Alarm OBJECT-TYPE
    SYNTAX   INTEGER{disabled(0), enabled(1)}
    MAX-ACCESS  read-write
    STATUS   current
    DESCRIPTION "Alarm of rectifier165 Enabled(1) or Disabled (0)"
    ::= {psRelay1Masks 324}

r1VBV166Alarm OBJECT-TYPE
    SYNTAX   INTEGER{disabled(0), enabled(1)}
    MAX-ACCESS  read-write
    STATUS   current
    DESCRIPTION "Alarm of rectifier166 Enabled(1) or Disabled (0)"
    ::= {psRelay1Masks 325}

r1VBV167Alarm OBJECT-TYPE
    SYNTAX   INTEGER{disabled(0), enabled(1)}
    MAX-ACCESS  read-write
    STATUS   current
    DESCRIPTION "Alarm of rectifier167 Enabled(1) or Disabled (0)"
    ::= {psRelay1Masks 326}

r1VBV168Alarm OBJECT-TYPE
    SYNTAX   INTEGER{disabled(0), enabled(1)}
    MAX-ACCESS  read-write
    STATUS   current
    DESCRIPTION "Alarm of rectifier168 Enabled(1) or Disabled (0)"
    ::= {psRelay1Masks 327}

r1VBV169Alarm OBJECT-TYPE
    SYNTAX   INTEGER{disabled(0), enabled(1)}
    MAX-ACCESS  read-write
    STATUS   current
    DESCRIPTION "Alarm of rectifier169 Enabled(1) or Disabled (0)"
    ::= {psRelay1Masks 328}

r1VBV170Alarm OBJECT-TYPE
    SYNTAX   INTEGER{disabled(0), enabled(1)}
    MAX-ACCESS  read-write
    STATUS   current
    DESCRIPTION "Alarm of rectifier170 Enabled(1) or Disabled (0)"
    ::= {psRelay1Masks 329}

r1VBV171Alarm OBJECT-TYPE
    SYNTAX   INTEGER{disabled(0), enabled(1)}
    MAX-ACCESS  read-write
    STATUS   current
    DESCRIPTION "Alarm of rectifier171 Enabled(1) or Disabled (0)"
    ::= {psRelay1Masks 330}

r1VBV172Alarm OBJECT-TYPE
    SYNTAX   INTEGER{disabled(0), enabled(1)}
    MAX-ACCESS  read-write
    STATUS   current
    DESCRIPTION "Alarm of rectifier172 Enabled(1) or Disabled (0)"
    ::= {psRelay1Masks 331}

r1VBV173Alarm OBJECT-TYPE
    SYNTAX   INTEGER{disabled(0), enabled(1)}
    MAX-ACCESS  read-write
    STATUS   current
    DESCRIPTION "Alarm of rectifier173 Enabled(1) or Disabled (0)"
    ::= {psRelay1Masks 332}

r1VBV174Alarm OBJECT-TYPE
    SYNTAX   INTEGER{disabled(0), enabled(1)}
    MAX-ACCESS  read-write
    STATUS   current
    DESCRIPTION "Alarm of rectifier174 Enabled(1) or Disabled (0)"
    ::= {psRelay1Masks 333}

r1VBV175Alarm OBJECT-TYPE
    SYNTAX   INTEGER{disabled(0), enabled(1)}
    MAX-ACCESS  read-write
    STATUS   current
    DESCRIPTION "Alarm of rectifier175 Enabled(1) or Disabled (0)"
    ::= {psRelay1Masks 334}

r1VBV176Alarm OBJECT-TYPE
    SYNTAX   INTEGER{disabled(0), enabled(1)}
    MAX-ACCESS  read-write
    STATUS   current
    DESCRIPTION "Alarm of rectifier176 Enabled(1) or Disabled (0)"
    ::= {psRelay1Masks 335}

r1VBV177Alarm OBJECT-TYPE
    SYNTAX   INTEGER{disabled(0), enabled(1)}
    MAX-ACCESS  read-write
    STATUS   current
    DESCRIPTION "Alarm of rectifier177 Enabled(1) or Disabled (0)"
    ::= {psRelay1Masks 336}

r1VBV178Alarm OBJECT-TYPE
    SYNTAX   INTEGER{disabled(0), enabled(1)}
    MAX-ACCESS  read-write
    STATUS   current
    DESCRIPTION "Alarm of rectifier178 Enabled(1) or Disabled (0)"
    ::= {psRelay1Masks 337}

r1VBV179Alarm OBJECT-TYPE
    SYNTAX   INTEGER{disabled(0), enabled(1)}
    MAX-ACCESS  read-write
    STATUS   current
    DESCRIPTION "Alarm of rectifier179 Enabled(1) or Disabled (0)"
    ::= {psRelay1Masks 338}

r1VBV180Alarm OBJECT-TYPE
    SYNTAX   INTEGER{disabled(0), enabled(1)}
    MAX-ACCESS  read-write
    STATUS   current
    DESCRIPTION "Alarm of rectifier180 Enabled(1) or Disabled (0)"
    ::= {psRelay1Masks 339}

r1VBVNoReserve OBJECT-TYPE
    SYNTAX   INTEGER{disabled(0), enabled(1)}
    MAX-ACCESS  read-write
    STATUS   current
    DESCRIPTION "Enabled(1) or Disabled (0)"
    ::= {psRelay1Masks 340}

r1VBVHighEfficiency OBJECT-TYPE
    SYNTAX   INTEGER{disabled(0), enabled(1)}
    MAX-ACCESS  read-write
    STATUS   current
    DESCRIPTION "Enabled(1) or Disabled (0)"
    ::= {psRelay1Masks 341}

--PhasesAlarm in psRelay1Masks
r1Phase1Alarm OBJECT-TYPE
    SYNTAX   INTEGER{disabled(0), enabled(1)}
    MAX-ACCESS  read-write
    STATUS   current
    DESCRIPTION "Enabled(1) or Disabled (0)"
    ::= {psRelay1Masks 352}

r1Phase2Alarm OBJECT-TYPE
    SYNTAX   INTEGER{disabled(0), enabled(1)}
    MAX-ACCESS  read-write
    STATUS   current
    DESCRIPTION "Enabled(1) or Disabled (0)"
    ::= {psRelay1Masks 353}

r1Phase3Alarm OBJECT-TYPE
    SYNTAX   INTEGER{disabled(0), enabled(1)}
    MAX-ACCESS  read-write
    STATUS   current
    DESCRIPTION "Enabled(1) or Disabled (0)"
    ::= {psRelay1Masks 354}

r1MainsSensorError OBJECT-TYPE
    SYNTAX   INTEGER{disabled(0), enabled(1)}
    MAX-ACCESS  read-write
    STATUS   current
    DESCRIPTION "Enabled(1) or Disabled (0)"
    ::= {psRelay1Masks 355}

r1LightProtectionAlarm OBJECT-TYPE
    SYNTAX   INTEGER{disabled(0), enabled(1)}
    MAX-ACCESS  read-write
    STATUS   current
    DESCRIPTION "Enabled(1) or Disabled (0)"
    ::= {psRelay1Masks 356}

--Ambience Temperature in psRelay1Masks
r1LowTemperature OBJECT-TYPE
    SYNTAX   INTEGER{disabled(0), enabled(1)}
    MAX-ACCESS  read-write
    STATUS   current
    DESCRIPTION "Enabled(1) or Disabled (0)"
    ::= {psRelay1Masks 384}

r1HighTemperature OBJECT-TYPE
    SYNTAX   INTEGER{disabled(0), enabled(1)}
    MAX-ACCESS  read-write
    STATUS   current
    DESCRIPTION "Enabled(1) or Disabled (0)"
    ::= {psRelay1Masks 385}

r1TemperatureSensorError OBJECT-TYPE
    SYNTAX   INTEGER{disabled(0), enabled(1)}
    MAX-ACCESS  read-write
    STATUS   current
    DESCRIPTION "Enabled(1) or Disabled (0)"
    ::= {psRelay1Masks 386}

--DryContacts in psRelay1Masks
r1DryContact1 OBJECT-TYPE
    SYNTAX   INTEGER{disabled(0), enabled(1)}
    MAX-ACCESS  read-write
    STATUS   current
    DESCRIPTION "Enabled(1) or Disabled (0)"
    ::= {psRelay1Masks 416}

r1DryContact2 OBJECT-TYPE
    SYNTAX   INTEGER{disabled(0), enabled(1)}
    MAX-ACCESS  read-write
    STATUS   current
    DESCRIPTION "Enabled(1) or Disabled (0)"
    ::= {psRelay1Masks 417}

r1DryContact3 OBJECT-TYPE
    SYNTAX   INTEGER{disabled(0), enabled(1)}
    MAX-ACCESS  read-write
    STATUS   current
    DESCRIPTION "Enabled(1) or Disabled (0)"
    ::= {psRelay1Masks 418}

r1DryContact4 OBJECT-TYPE
    SYNTAX   INTEGER{disabled(0), enabled(1)}
    MAX-ACCESS  read-write
    STATUS   current
    DESCRIPTION "Enabled(1) or Disabled (0)"
    ::= {psRelay1Masks 419}

r1DryContact5 OBJECT-TYPE
    SYNTAX   INTEGER{disabled(0), enabled(1)}
    MAX-ACCESS  read-write
    STATUS   current
    DESCRIPTION "Enabled(1) or Disabled (0)"
    ::= {psRelay1Masks 420}

r1DryContact6 OBJECT-TYPE
    SYNTAX   INTEGER{disabled(0), enabled(1)}
    MAX-ACCESS  read-write
    STATUS   current
    DESCRIPTION "Enabled(1) or Disabled (0)"
    ::= {psRelay1Masks 421}

r1DryContact7 OBJECT-TYPE
    SYNTAX   INTEGER{disabled(0), enabled(1)}
    MAX-ACCESS  read-write
    STATUS   current
    DESCRIPTION "Enabled(1) or Disabled (0)"
    ::= {psRelay1Masks 422}

r1DryContact8 OBJECT-TYPE
    SYNTAX   INTEGER{disabled(0), enabled(1)}
    MAX-ACCESS  read-write
    STATUS   current
    DESCRIPTION "Enabled(1) or Disabled (0)"
    ::= {psRelay1Masks 423}

r1DryContact9 OBJECT-TYPE
    SYNTAX   INTEGER{disabled(0), enabled(1)}
    MAX-ACCESS  read-write
    STATUS   current
    DESCRIPTION "Enabled(1) or Disabled (0)"
    ::= {psRelay1Masks 424}

r1DryContact10 OBJECT-TYPE
    SYNTAX   INTEGER{disabled(0), enabled(1)}
    MAX-ACCESS  read-write
    STATUS   current
    DESCRIPTION "Enabled(1) or Disabled (0)"
    ::= {psRelay1Masks 425}

r1DryContact11 OBJECT-TYPE
    SYNTAX   INTEGER{disabled(0), enabled(1)}
    MAX-ACCESS  read-write
    STATUS   current
    DESCRIPTION "Enabled(1) or Disabled (0)"
    ::= {psRelay1Masks 426}

r1DryContact12 OBJECT-TYPE
    SYNTAX   INTEGER{disabled(0), enabled(1)}
    MAX-ACCESS  read-write
    STATUS   current
    DESCRIPTION "Enabled(1) or Disabled (0)"
    ::= {psRelay1Masks 427}

r1DryContact13 OBJECT-TYPE
    SYNTAX   INTEGER{disabled(0), enabled(1)}
    MAX-ACCESS  read-write
    STATUS   current
    DESCRIPTION "Enabled(1) or Disabled (0)"
    ::= {psRelay1Masks 428}

r1DryContact14 OBJECT-TYPE
    SYNTAX   INTEGER{disabled(0), enabled(1)}
    MAX-ACCESS  read-write
    STATUS   current
    DESCRIPTION "Enabled(1) or Disabled (0)"
    ::= {psRelay1Masks 429}

r1DryContact15 OBJECT-TYPE
    SYNTAX   INTEGER{disabled(0), enabled(1)}
    MAX-ACCESS  read-write
    STATUS   current
    DESCRIPTION "Enabled(1) or Disabled (0)"
    ::= {psRelay1Masks 430}

r1DryContact16 OBJECT-TYPE
    SYNTAX   INTEGER{disabled(0), enabled(1)}
    MAX-ACCESS  read-write
    STATUS   current
    DESCRIPTION "Enabled(1) or Disabled (0)"
    ::= {psRelay1Masks 431}

-- --------------------------------------

r1BatteryLiIonAlarm OBJECT-TYPE  
    SYNTAX   INTEGER{disabled(0), enabled(1)}
    MAX-ACCESS  read-write
    STATUS   current
    DESCRIPTION "Enabled(1) or Disabled (0)"
    ::= {psRelay1Masks 480}

--нет связи с BMS
r1BatteryBMSComFail OBJECT-TYPE  
    SYNTAX   INTEGER{disabled(0), enabled(1)}
    MAX-ACCESS  read-write
    STATUS   current
    DESCRIPTION "Enabled(1) or Disabled (0)"
    ::= {psRelay1Masks 481}

-- --------------------------------------

--InternalErrors in psRelay2Masks
r2InternallError OBJECT-TYPE
    SYNTAX   INTEGER{disabled(0), enabled(1)}
    MAX-ACCESS  read-write
    STATUS   current
    DESCRIPTION "Enabled(1) or Disabled (0)"
    ::= {psRelay2Masks 1}

--OutputAlarms in psRelay2Masks
r2LoadUnderVoltageAlarm OBJECT-TYPE
    SYNTAX   INTEGER{disabled(0), enabled(1)}
    MAX-ACCESS  read-write
    STATUS   current
    DESCRIPTION "Enabled(1) or Disabled (0)"
    ::= {psRelay2Masks 32}

r2LoadOverVoltageAlarm OBJECT-TYPE
    SYNTAX   INTEGER{disabled(0), enabled(1)}
    MAX-ACCESS  read-write
    STATUS   current
    DESCRIPTION "Enabled(1) or Disabled (0)"
    ::= {psRelay2Masks 33}

r2Termocompensation OBJECT-TYPE
    SYNTAX   INTEGER{disabled(0), enabled(1)}
    MAX-ACCESS  read-write
    STATUS   current
    DESCRIPTION "Enabled(1) or Disabled (0)"
    ::= {psRelay2Masks 34}

--LoadFuses in psRelay2Masks
r2LoadFuses1 OBJECT-TYPE
    SYNTAX   INTEGER{disabled(0), enabled(1)}
    MAX-ACCESS  read-write
    STATUS   current
    DESCRIPTION "Enabled(1) or Disabled (0)"
    ::= {psRelay2Masks 35}

r2LoadFuses2 OBJECT-TYPE
    SYNTAX   INTEGER{disabled(0), enabled(1)}
    MAX-ACCESS  read-write
    STATUS   current
    DESCRIPTION "Enabled(1) or Disabled (0)"
    ::= {psRelay2Masks 36}

r2LoadFuses3 OBJECT-TYPE
    SYNTAX   INTEGER{disabled(0), enabled(1)}
    MAX-ACCESS  read-write
    STATUS   current
    DESCRIPTION "Enabled(1) or Disabled (0)"
    ::= {psRelay2Masks 37}

r2LoadFuses4 OBJECT-TYPE
    SYNTAX   INTEGER{disabled(0), enabled(1)}
    MAX-ACCESS  read-write
    STATUS   current
    DESCRIPTION "Enabled(1) or Disabled (0)"
    ::= {psRelay2Masks 38}

r2LoadFuses5 OBJECT-TYPE
    SYNTAX   INTEGER{disabled(0), enabled(1)}
    MAX-ACCESS  read-write
    STATUS   current
    DESCRIPTION "Enabled(1) or Disabled (0)"
    ::= {psRelay2Masks 39}

r2LoadFuses6 OBJECT-TYPE
    SYNTAX   INTEGER{disabled(0), enabled(1)}
    MAX-ACCESS  read-write
    STATUS   current
    DESCRIPTION "Enabled(1) or Disabled (0)"
    ::= {psRelay2Masks 40}

r2LoadFuses7 OBJECT-TYPE
    SYNTAX   INTEGER{disabled(0), enabled(1)}
    MAX-ACCESS  read-write
    STATUS   current
    DESCRIPTION "Enabled(1) or Disabled (0)"
    ::= {psRelay2Masks 41}

r2LoadFuses8 OBJECT-TYPE
    SYNTAX   INTEGER{disabled(0), enabled(1)}
    MAX-ACCESS  read-write
    STATUS   current
    DESCRIPTION "Enabled(1) or Disabled (0)"
    ::= {psRelay2Masks 42}

r2LoadFuses9 OBJECT-TYPE
    SYNTAX   INTEGER{disabled(0), enabled(1)}
    MAX-ACCESS  read-write
    STATUS   current
    DESCRIPTION "Enabled(1) or Disabled (0)"
    ::= {psRelay2Masks 43}

r2LoadFuses10 OBJECT-TYPE
    SYNTAX   INTEGER{disabled(0), enabled(1)}
    MAX-ACCESS  read-write
    STATUS   current
    DESCRIPTION "Enabled(1) or Disabled (0)"
    ::= {psRelay2Masks 44}

r2LoadFuses11 OBJECT-TYPE
    SYNTAX   INTEGER{disabled(0), enabled(1)}
    MAX-ACCESS  read-write
    STATUS   current
    DESCRIPTION "Enabled(1) or Disabled (0)"
    ::= {psRelay2Masks 45}

r2LoadFuses12 OBJECT-TYPE
    SYNTAX   INTEGER{disabled(0), enabled(1)}
    MAX-ACCESS  read-write
    STATUS   current
    DESCRIPTION "Enabled(1) or Disabled (0)"
    ::= {psRelay2Masks 46}

r2LoadFuses13 OBJECT-TYPE
    SYNTAX   INTEGER{disabled(0), enabled(1)}
    MAX-ACCESS  read-write
    STATUS   current
    DESCRIPTION "Enabled(1) or Disabled (0)"
    ::= {psRelay2Masks 47}

r2LoadFuses14 OBJECT-TYPE
    SYNTAX   INTEGER{disabled(0), enabled(1)}
    MAX-ACCESS  read-write
    STATUS   current
    DESCRIPTION "Enabled(1) or Disabled (0)"
    ::= {psRelay2Masks 48}

r2LoadFuses15 OBJECT-TYPE
    SYNTAX   INTEGER{disabled(0), enabled(1)}
    MAX-ACCESS  read-write
    STATUS   current
    DESCRIPTION "Enabled(1) or Disabled (0)"
    ::= {psRelay2Masks 49}

r2LoadFuses16 OBJECT-TYPE
    SYNTAX   INTEGER{disabled(0), enabled(1)}
    MAX-ACCESS  read-write
    STATUS   current
    DESCRIPTION "Enabled(1) or Disabled (0)"
    ::= {psRelay2Masks 50}

r2LoadFuses17 OBJECT-TYPE
    SYNTAX   INTEGER{disabled(0), enabled(1)}
    MAX-ACCESS  read-write
    STATUS   current
    DESCRIPTION "Enabled(1) or Disabled (0)"
    ::= {psRelay2Masks 51}

r2LoadFuses18 OBJECT-TYPE
    SYNTAX   INTEGER{disabled(0), enabled(1)}
    MAX-ACCESS  read-write
    STATUS   current
    DESCRIPTION "Enabled(1) or Disabled (0)"
    ::= {psRelay2Masks 52}

r2LoadFuses19 OBJECT-TYPE
    SYNTAX   INTEGER{disabled(0), enabled(1)}
    MAX-ACCESS  read-write
    STATUS   current
    DESCRIPTION "Enabled(1) or Disabled (0)"
    ::= {psRelay2Masks 53}

r2LoadFuses20 OBJECT-TYPE
    SYNTAX   INTEGER{disabled(0), enabled(1)}
    MAX-ACCESS  read-write
    STATUS   current
    DESCRIPTION "Enabled(1) or Disabled (0)"
    ::= {psRelay2Masks 54}

r2LoadFuses21 OBJECT-TYPE
    SYNTAX   INTEGER{disabled(0), enabled(1)}
    MAX-ACCESS  read-write
    STATUS   current
    DESCRIPTION "Enabled(1) or Disabled (0)"
    ::= {psRelay2Masks 55}

r2LoadFuses22 OBJECT-TYPE
    SYNTAX   INTEGER{disabled(0), enabled(1)}
    MAX-ACCESS  read-write
    STATUS   current
    DESCRIPTION "Enabled(1) or Disabled (0)"
    ::= {psRelay2Masks 56}

r2LoadFuses23 OBJECT-TYPE
    SYNTAX   INTEGER{disabled(0), enabled(1)}
    MAX-ACCESS  read-write
    STATUS   current
    DESCRIPTION "Enabled(1) or Disabled (0)"
    ::= {psRelay2Masks 57}

r2LoadFuses24 OBJECT-TYPE
    SYNTAX   INTEGER{disabled(0), enabled(1)}
    MAX-ACCESS  read-write
    STATUS   current
    DESCRIPTION "Enabled(1) or Disabled (0)"
    ::= {psRelay2Masks 58}

r2LoadFuses25 OBJECT-TYPE
    SYNTAX   INTEGER{disabled(0), enabled(1)}
    MAX-ACCESS  read-write
    STATUS   current
    DESCRIPTION "Enabled(1) or Disabled (0)"
    ::= {psRelay2Masks 59}

r2LoadFuses26 OBJECT-TYPE
    SYNTAX   INTEGER{disabled(0), enabled(1)}
    MAX-ACCESS  read-write
    STATUS   current
    DESCRIPTION "Enabled(1) or Disabled (0)"
    ::= {psRelay2Masks 60}

r2LoadFuses27 OBJECT-TYPE
    SYNTAX   INTEGER{disabled(0), enabled(1)}
    MAX-ACCESS  read-write
    STATUS   current
    DESCRIPTION "Enabled(1) or Disabled (0)"
    ::= {psRelay2Masks 61}

r2LoadFuses28 OBJECT-TYPE
    SYNTAX   INTEGER{disabled(0), enabled(1)}
    MAX-ACCESS  read-write
    STATUS   current
    DESCRIPTION "Enabled(1) or Disabled (0)"
    ::= {psRelay2Masks 62}

r2LoadFuses29 OBJECT-TYPE
    SYNTAX   INTEGER{disabled(0), enabled(1)}
    MAX-ACCESS  read-write
    STATUS   current
    DESCRIPTION "Enabled(1) or Disabled (0)"
    ::= {psRelay2Masks 63}

r2LoadFuses30 OBJECT-TYPE
    SYNTAX   INTEGER{disabled(0), enabled(1)}
    MAX-ACCESS  read-write
    STATUS   current
    DESCRIPTION "Enabled(1) or Disabled (0)"
    ::= {psRelay2Masks 64}

r2LoadFuses31 OBJECT-TYPE
    SYNTAX   INTEGER{disabled(0), enabled(1)}
    MAX-ACCESS  read-write
    STATUS   current
    DESCRIPTION "Enabled(1) or Disabled (0)"
    ::= {psRelay2Masks 65}

r2LoadFuses32 OBJECT-TYPE
    SYNTAX   INTEGER{disabled(0), enabled(1)}
    MAX-ACCESS  read-write
    STATUS   current
    DESCRIPTION "Enabled(1) or Disabled (0)"
    ::= {psRelay2Masks 66}

r2LoadFuses33 OBJECT-TYPE
    SYNTAX   INTEGER{disabled(0), enabled(1)}
    MAX-ACCESS  read-write
    STATUS   current
    DESCRIPTION "Enabled(1) or Disabled (0)"
    ::= {psRelay2Masks 67}

r2LoadFuses34 OBJECT-TYPE
    SYNTAX   INTEGER{disabled(0), enabled(1)}
    MAX-ACCESS  read-write
    STATUS   current
    DESCRIPTION "Enabled(1) or Disabled (0)"
    ::= {psRelay2Masks 68}

r2LoadFuses35 OBJECT-TYPE
    SYNTAX   INTEGER{disabled(0), enabled(1)}
    MAX-ACCESS  read-write
    STATUS   current
    DESCRIPTION "Enabled(1) or Disabled (0)"
    ::= {psRelay2Masks 69}

r2LoadFuses36 OBJECT-TYPE
    SYNTAX   INTEGER{disabled(0), enabled(1)}
    MAX-ACCESS  read-write
    STATUS   current
    DESCRIPTION "Enabled(1) or Disabled (0)"
    ::= {psRelay2Masks 70}

r2LoadFuses37 OBJECT-TYPE
    SYNTAX   INTEGER{disabled(0), enabled(1)}
    MAX-ACCESS  read-write
    STATUS   current
    DESCRIPTION "Enabled(1) or Disabled (0)"
    ::= {psRelay2Masks 71}

r2LoadFuses38 OBJECT-TYPE
    SYNTAX   INTEGER{disabled(0), enabled(1)}
    MAX-ACCESS  read-write
    STATUS   current
    DESCRIPTION "Enabled(1) or Disabled (0)"
    ::= {psRelay2Masks 72}

r2LoadFuses39 OBJECT-TYPE
    SYNTAX   INTEGER{disabled(0), enabled(1)}
    MAX-ACCESS  read-write
    STATUS   current
    DESCRIPTION "Enabled(1) or Disabled (0)"
    ::= {psRelay2Masks 73}

r2LoadFuses40 OBJECT-TYPE
    SYNTAX   INTEGER{disabled(0), enabled(1)}
    MAX-ACCESS  read-write
    STATUS   current
    DESCRIPTION "Enabled(1) or Disabled (0)"
    ::= {psRelay2Masks 74}

r2LoadFuses41 OBJECT-TYPE
    SYNTAX   INTEGER{disabled(0), enabled(1)}
    MAX-ACCESS  read-write
    STATUS   current
    DESCRIPTION "Enabled(1) or Disabled (0)"
    ::= {psRelay2Masks 75}

r2LoadFuses42 OBJECT-TYPE
    SYNTAX   INTEGER{disabled(0), enabled(1)}
    MAX-ACCESS  read-write
    STATUS   current
    DESCRIPTION "Enabled(1) or Disabled (0)"
    ::= {psRelay2Masks 76}

r2LoadFuses43 OBJECT-TYPE
    SYNTAX   INTEGER{disabled(0), enabled(1)}
    MAX-ACCESS  read-write
    STATUS   current
    DESCRIPTION "Enabled(1) or Disabled (0)"
    ::= {psRelay2Masks 77}

r2LoadFuses44 OBJECT-TYPE
    SYNTAX   INTEGER{disabled(0), enabled(1)}
    MAX-ACCESS  read-write
    STATUS   current
    DESCRIPTION "Enabled(1) or Disabled (0)"
    ::= {psRelay2Masks 78}

r2LoadFuses45 OBJECT-TYPE
    SYNTAX   INTEGER{disabled(0), enabled(1)}
    MAX-ACCESS  read-write
    STATUS   current
    DESCRIPTION "Enabled(1) or Disabled (0)"
    ::= {psRelay2Masks 79}

r2LoadFuses46 OBJECT-TYPE
    SYNTAX   INTEGER{disabled(0), enabled(1)}
    MAX-ACCESS  read-write
    STATUS   current
    DESCRIPTION "Enabled(1) or Disabled (0)"
    ::= {psRelay2Masks 80}

r2LoadFuses47 OBJECT-TYPE
    SYNTAX   INTEGER{disabled(0), enabled(1)}
    MAX-ACCESS  read-write
    STATUS   current
    DESCRIPTION "Enabled(1) or Disabled (0)"
    ::= {psRelay2Masks 81}

r2LoadFuses48 OBJECT-TYPE
    SYNTAX   INTEGER{disabled(0), enabled(1)}
    MAX-ACCESS  read-write
    STATUS   current
    DESCRIPTION "Enabled(1) or Disabled (0)"
    ::= {psRelay2Masks 82}

r2LoadFuses49 OBJECT-TYPE
    SYNTAX   INTEGER{disabled(0), enabled(1)}
    MAX-ACCESS  read-write
    STATUS   current
    DESCRIPTION "Enabled(1) or Disabled (0)"
    ::= {psRelay2Masks 83}

r2LoadFuses50 OBJECT-TYPE
    SYNTAX   INTEGER{disabled(0), enabled(1)}
    MAX-ACCESS  read-write
    STATUS   current
    DESCRIPTION "Enabled(1) or Disabled (0)"
    ::= {psRelay2Masks 84}

r2LoadFuses51 OBJECT-TYPE
    SYNTAX   INTEGER{disabled(0), enabled(1)}
    MAX-ACCESS  read-write
    STATUS   current
    DESCRIPTION "Enabled(1) or Disabled (0)"
    ::= {psRelay2Masks 85}

r2LoadFuses52 OBJECT-TYPE
    SYNTAX   INTEGER{disabled(0), enabled(1)}
    MAX-ACCESS  read-write
    STATUS   current
    DESCRIPTION "Enabled(1) or Disabled (0)"
    ::= {psRelay2Masks 86}

r2UKDVAlarm OBJECT-TYPE
    SYNTAX   INTEGER{disabled(0), enabled(1)}
    MAX-ACCESS  read-write
    STATUS   current
    DESCRIPTION "Enabled(1) or Disabled (0)"
    ::= {psRelay2Masks 87}

--Battery Events in psRelay2Masks
r2BatteryDischarge OBJECT-TYPE
    SYNTAX   INTEGER{disabled(0), enabled(1)}
    MAX-ACCESS  read-write
    STATUS   current
    DESCRIPTION "Enabled(1) or Disabled (0)"
    ::= {psRelay2Masks 96}

r2LowBatteryVoltage OBJECT-TYPE
    SYNTAX   INTEGER{disabled(0), enabled(1)}
    MAX-ACCESS  read-write
    STATUS   current
    DESCRIPTION "Enabled(1) or Disabled (0)"
    ::= {psRelay2Masks 97}

r2BatteryCharge OBJECT-TYPE
    SYNTAX   INTEGER{disabled(0), enabled(1)}
    MAX-ACCESS  read-write
    STATUS   current
    DESCRIPTION "Enabled(1) or Disabled (0)"
    ::= {psRelay2Masks 98}

r2BatteryBoost OBJECT-TYPE
    SYNTAX   INTEGER{disabled(0), enabled(1)}
    MAX-ACCESS  read-write
    STATUS   current
    DESCRIPTION "Enabled(1) or Disabled (0)"
    ::= {psRelay2Masks 99}

r2BatteryFloat OBJECT-TYPE
    SYNTAX   INTEGER{disabled(0), enabled(1)}
    MAX-ACCESS  read-write
    STATUS   current
    DESCRIPTION "Enabled(1) or Disabled (0)"
    ::= {psRelay2Masks 100}

r2BatteryEqualize OBJECT-TYPE
    SYNTAX   INTEGER{disabled(0), enabled(1)}
    MAX-ACCESS  read-write
    STATUS   current
    DESCRIPTION "Enabled(1) or Disabled (0)"
    ::= {psRelay2Masks 101}

r2BatteryTest OBJECT-TYPE
    SYNTAX   INTEGER{disabled(0), enabled(1)}
    MAX-ACCESS  read-write
    STATUS   current
    DESCRIPTION "Enabled(1) or Disabled (0)"
    ::= {psRelay2Masks 102}

r2BatteryFuse1Off OBJECT-TYPE
    SYNTAX   INTEGER{disabled(0), enabled(1)}
    MAX-ACCESS  read-write
    STATUS   current
    DESCRIPTION "Enabled(1) or Disabled (0)"
    ::= {psRelay2Masks 103}

r2BatteryFuse2Off OBJECT-TYPE
    SYNTAX   INTEGER{disabled(0), enabled(1)}
    MAX-ACCESS  read-write
    STATUS   current
    DESCRIPTION "Enabled(1) or Disabled (0)"
    ::= {psRelay2Masks 104}

r2BatteryFuse3Off OBJECT-TYPE
    SYNTAX   INTEGER{disabled(0), enabled(1)}
    MAX-ACCESS  read-write
    STATUS   current
    DESCRIPTION "Enabled(1) or Disabled (0)"
    ::= {psRelay2Masks 105}

r2BatteryFuse4Off OBJECT-TYPE
    SYNTAX   INTEGER{disabled(0), enabled(1)}
    MAX-ACCESS  read-write
    STATUS   current
    DESCRIPTION "Enabled(1) or Disabled (0)"
    ::= {psRelay2Masks 106}

---------------------------------------------------

r2BatteryBlockElGr1Alarm OBJECT-TYPE
    SYNTAX   INTEGER{disabled(0), enabled(1)}
    MAX-ACCESS  read-write
    STATUS   current
    DESCRIPTION "Enabled(1) or Disabled (0)"
    ::= {psRelay2Masks 111}

r2BatteryBlockElGr2Alarm OBJECT-TYPE
    SYNTAX   INTEGER{disabled(0), enabled(1)}
    MAX-ACCESS  read-write
    STATUS   current
    DESCRIPTION "Enabled(1) or Disabled (0)"
    ::= {psRelay2Masks 112}

r2BatteryBlockElGr3Alarm OBJECT-TYPE
    SYNTAX   INTEGER{disabled(0), enabled(1)}
    MAX-ACCESS  read-write
    STATUS   current
    DESCRIPTION "Enabled(1) or Disabled (0)"
    ::= {psRelay2Masks 113}

r2BatteryBlockElGr4Alarm OBJECT-TYPE
    SYNTAX   INTEGER{disabled(0), enabled(1)}
    MAX-ACCESS  read-write
    STATUS   current
    DESCRIPTION "Enabled(1) or Disabled (0)"
    ::= {psRelay2Masks 114}
----------------------------------------------------

r2UPKBAlarm OBJECT-TYPE
    SYNTAX   INTEGER{disabled(0), enabled(1)}
    MAX-ACCESS  read-write
    STATUS   current
    DESCRIPTION "Enabled(1) or Disabled (0)"
    ::= {psRelay2Masks 119}

r2ChargeCurrentLess1A OBJECT-TYPE
    SYNTAX   INTEGER{disabled(0), enabled(1)}
    MAX-ACCESS  read-write
    STATUS   current
    DESCRIPTION "Enabled(1) or Disabled (0)"
    ::= {psRelay2Masks 120}

r2ChargeCurrentLess2A OBJECT-TYPE
    SYNTAX   INTEGER{disabled(0), enabled(1)}
    MAX-ACCESS  read-write
    STATUS   current
    DESCRIPTION "Enabled(1) or Disabled (0)"
    ::= {psRelay2Masks 121}

r2ChargeCurrentLess3A OBJECT-TYPE
    SYNTAX   INTEGER{disabled(0), enabled(1)}
    MAX-ACCESS  read-write
    STATUS   current
    DESCRIPTION "Enabled(1) or Disabled (0)"
    ::= {psRelay2Masks 122}

r2ChargeCurrentLess4A OBJECT-TYPE
    SYNTAX   INTEGER{disabled(0), enabled(1)}
    MAX-ACCESS  read-write
    STATUS   current
    DESCRIPTION "Enabled(1) or Disabled (0)"
    ::= {psRelay2Masks 123}

r2ChargeCurrentLess5A OBJECT-TYPE
    SYNTAX   INTEGER{disabled(0), enabled(1)}
    MAX-ACCESS  read-write
    STATUS   current
    DESCRIPTION "Enabled(1) or Disabled (0)"
    ::= {psRelay2Masks 124}

r2BatteryOverheat OBJECT-TYPE
    SYNTAX   INTEGER{disabled(0), enabled(1)}
    MAX-ACCESS  read-write
    STATUS   current
    DESCRIPTION "Enabled(1) or Disabled (0)"
    ::= {psRelay2Masks 125}

-------------------------------------------------------------------------------------------
-------------------------------------------------------------------------------------------
r2BatteryShortTest OBJECT-TYPE
    SYNTAX   INTEGER{disabled(0), enabled(1)}
    MAX-ACCESS  read-write
    STATUS   current
    DESCRIPTION "Enabled(1) or Disabled (0)"
    ::= {psRelay2Masks 126}

r2BatteryShortTestFail OBJECT-TYPE  
    SYNTAX   INTEGER{disabled(0), enabled(1)}
    MAX-ACCESS  read-write
    STATUS   current
    DESCRIPTION "Enabled(1) or Disabled (0)"
    ::= {psRelay2Masks 127}

-------------------------------------------------------------------------------------------
-------------------------------------------------------------------------------------------

r2BLVDoff OBJECT-TYPE
    SYNTAX   INTEGER{disabled(0), enabled(1)}
    MAX-ACCESS  read-write
    STATUS   current
    DESCRIPTION "Enabled(1) or Disabled (0)"
    ::= {psRelay2Masks 128}

r2LLVD1off OBJECT-TYPE
    SYNTAX   INTEGER{disabled(0), enabled(1)}
    MAX-ACCESS  read-write
    STATUS   current
    DESCRIPTION "Enabled(1) or Disabled (0)"
    ::= {psRelay2Masks 129}

r2LLVD2off OBJECT-TYPE
    SYNTAX   INTEGER{disabled(0), enabled(1)}
    MAX-ACCESS  read-write
    STATUS   current
    DESCRIPTION "Enabled(1) or Disabled (0)"
    ::= {psRelay2Masks 130}

--VBVAlarm in psRelay2Masks
r2VBV1Alarm OBJECT-TYPE
    SYNTAX   INTEGER{disabled(0), enabled(1)}
    MAX-ACCESS  read-write
    STATUS   current
    DESCRIPTION "Alarm of rectifier1 Enabled(1) or Disabled (0)"
    ::= {psRelay2Masks 160}

r2VBV2Alarm OBJECT-TYPE
    SYNTAX   INTEGER{disabled(0), enabled(1)}
    MAX-ACCESS  read-write
    STATUS   current
    DESCRIPTION "Alarm of rectifier2 Enabled(1) or Disabled (0)"
    ::= {psRelay2Masks 161}

r2VBV3Alarm OBJECT-TYPE
    SYNTAX   INTEGER{disabled(0), enabled(1)}
    MAX-ACCESS  read-write
    STATUS   current
    DESCRIPTION "Alarm of rectifier3 Enabled(1) or Disabled (0)"
    ::= {psRelay2Masks 162}

r2VBV4Alarm OBJECT-TYPE
    SYNTAX   INTEGER{disabled(0), enabled(1)}
    MAX-ACCESS  read-write
    STATUS   current
    DESCRIPTION "Alarm of rectifier4 Enabled(1) or Disabled (0)"
    ::= {psRelay2Masks 163}

r2VBV5Alarm OBJECT-TYPE
    SYNTAX   INTEGER{disabled(0), enabled(1)}
    MAX-ACCESS  read-write
    STATUS   current
    DESCRIPTION "Alarm of rectifier5 Enabled(1) or Disabled (0)"
    ::= {psRelay2Masks 164}

r2VBV6Alarm OBJECT-TYPE
    SYNTAX   INTEGER{disabled(0), enabled(1)}
    MAX-ACCESS  read-write
    STATUS   current
    DESCRIPTION "Alarm of rectifier6 Enabled(1) or Disabled (0)"
    ::= {psRelay2Masks 165}

r2VBV7Alarm OBJECT-TYPE
    SYNTAX   INTEGER{disabled(0), enabled(1)}
    MAX-ACCESS  read-write
    STATUS   current
    DESCRIPTION "Alarm of rectifier7 Enabled(1) or Disabled (0)"
    ::= {psRelay2Masks 166}

r2VBV8Alarm OBJECT-TYPE
    SYNTAX   INTEGER{disabled(0), enabled(1)}
    MAX-ACCESS  read-write
    STATUS   current
    DESCRIPTION "Alarm of rectifier8 Enabled(1) or Disabled (0)"
    ::= {psRelay2Masks 167}

r2VBV9Alarm OBJECT-TYPE
    SYNTAX   INTEGER{disabled(0), enabled(1)}
    MAX-ACCESS  read-write
    STATUS   current
    DESCRIPTION "Alarm of rectifier9 Enabled(1) or Disabled (0)"
    ::= {psRelay2Masks 168}

r2VBV10Alarm OBJECT-TYPE
    SYNTAX   INTEGER{disabled(0), enabled(1)}
    MAX-ACCESS  read-write
    STATUS   current
    DESCRIPTION "Alarm of rectifier10 Enabled(1) or Disabled (0)"
    ::= {psRelay2Masks 169}

r2VBV11Alarm OBJECT-TYPE
    SYNTAX   INTEGER{disabled(0), enabled(1)}
    MAX-ACCESS  read-write
    STATUS   current
    DESCRIPTION "Alarm of rectifier11 Enabled(1) or Disabled (0)"
    ::= {psRelay2Masks 170}

r2VBV12Alarm OBJECT-TYPE
    SYNTAX   INTEGER{disabled(0), enabled(1)}
    MAX-ACCESS  read-write
    STATUS   current
    DESCRIPTION "Alarm of rectifier12 Enabled(1) or Disabled (0)"
    ::= {psRelay2Masks 171}

r2VBV13Alarm OBJECT-TYPE
    SYNTAX   INTEGER{disabled(0), enabled(1)}
    MAX-ACCESS  read-write
    STATUS   current
    DESCRIPTION "Alarm of rectifier13 Enabled(1) or Disabled (0)"
    ::= {psRelay2Masks 172}

r2VBV14Alarm OBJECT-TYPE
    SYNTAX   INTEGER{disabled(0), enabled(1)}
    MAX-ACCESS  read-write
    STATUS   current
    DESCRIPTION "Alarm of rectifier14 Enabled(1) or Disabled (0)"
    ::= {psRelay2Masks 173}

r2VBV15Alarm OBJECT-TYPE
    SYNTAX   INTEGER{disabled(0), enabled(1)}
    MAX-ACCESS  read-write
    STATUS   current
    DESCRIPTION "Alarm of rectifier15 Enabled(1) or Disabled (0)"
    ::= {psRelay2Masks 174}

r2VBV16Alarm OBJECT-TYPE
    SYNTAX   INTEGER{disabled(0), enabled(1)}
    MAX-ACCESS  read-write
    STATUS   current
    DESCRIPTION "Alarm of rectifier16 Enabled(1) or Disabled (0)"
    ::= {psRelay2Masks 175}

r2VBV17Alarm OBJECT-TYPE
    SYNTAX   INTEGER{disabled(0), enabled(1)}
    MAX-ACCESS  read-write
    STATUS   current
    DESCRIPTION "Alarm of rectifier17 Enabled(1) or Disabled (0)"
    ::= {psRelay2Masks 176}

r2VBV18Alarm OBJECT-TYPE
    SYNTAX   INTEGER{disabled(0), enabled(1)}
    MAX-ACCESS  read-write
    STATUS   current
    DESCRIPTION "Alarm of rectifier18 Enabled(1) or Disabled (0)"
    ::= {psRelay2Masks 177}

r2VBV19Alarm OBJECT-TYPE
    SYNTAX   INTEGER{disabled(0), enabled(1)}
    MAX-ACCESS  read-write
    STATUS   current
    DESCRIPTION "Alarm of rectifier19 Enabled(1) or Disabled (0)"
    ::= {psRelay2Masks 178}

r2VBV20Alarm OBJECT-TYPE
    SYNTAX   INTEGER{disabled(0), enabled(1)}
    MAX-ACCESS  read-write
    STATUS   current
    DESCRIPTION "Alarm of rectifier20 Enabled(1) or Disabled (0)"
    ::= {psRelay2Masks 179}

r2VBV21Alarm OBJECT-TYPE
    SYNTAX   INTEGER{disabled(0), enabled(1)}
    MAX-ACCESS  read-write
    STATUS   current
    DESCRIPTION "Alarm of rectifier21 Enabled(1) or Disabled (0)"
    ::= {psRelay2Masks 180}

r2VBV22Alarm OBJECT-TYPE
    SYNTAX   INTEGER{disabled(0), enabled(1)}
    MAX-ACCESS  read-write
    STATUS   current
    DESCRIPTION "Alarm of rectifier22 Enabled(1) or Disabled (0)"
    ::= {psRelay2Masks 181}

r2VBV23Alarm OBJECT-TYPE
    SYNTAX   INTEGER{disabled(0), enabled(1)}
    MAX-ACCESS  read-write
    STATUS   current
    DESCRIPTION "Alarm of rectifier23 Enabled(1) or Disabled (0)"
    ::= {psRelay2Masks 182}

r2VBV24Alarm OBJECT-TYPE
    SYNTAX   INTEGER{disabled(0), enabled(1)}
    MAX-ACCESS  read-write
    STATUS   current
    DESCRIPTION "Alarm of rectifier24 Enabled(1) or Disabled (0)"
    ::= {psRelay2Masks 183}

r2VBV25Alarm OBJECT-TYPE
    SYNTAX   INTEGER{disabled(0), enabled(1)}
    MAX-ACCESS  read-write
    STATUS   current
    DESCRIPTION "Alarm of rectifier25 Enabled(1) or Disabled (0)"
    ::= {psRelay2Masks 184}

r2VBV26Alarm OBJECT-TYPE
    SYNTAX   INTEGER{disabled(0), enabled(1)}
    MAX-ACCESS  read-write
    STATUS   current
    DESCRIPTION "Alarm of rectifier26 Enabled(1) or Disabled (0)"
    ::= {psRelay2Masks 185}

r2VBV27Alarm OBJECT-TYPE
    SYNTAX   INTEGER{disabled(0), enabled(1)}
    MAX-ACCESS  read-write
    STATUS   current
    DESCRIPTION "Alarm of rectifier27 Enabled(1) or Disabled (0)"
    ::= {psRelay2Masks 186}

r2VBV28Alarm OBJECT-TYPE
    SYNTAX   INTEGER{disabled(0), enabled(1)}
    MAX-ACCESS  read-write
    STATUS   current
    DESCRIPTION "Alarm of rectifier28 Enabled(1) or Disabled (0)"
    ::= {psRelay2Masks 187}

r2VBV29Alarm OBJECT-TYPE
    SYNTAX   INTEGER{disabled(0), enabled(1)}
    MAX-ACCESS  read-write
    STATUS   current
    DESCRIPTION "Alarm of rectifier29 Enabled(1) or Disabled (0)"
    ::= {psRelay2Masks 188}

r2VBV30Alarm OBJECT-TYPE
    SYNTAX   INTEGER{disabled(0), enabled(1)}
    MAX-ACCESS  read-write
    STATUS   current
    DESCRIPTION "Alarm of rectifier30 Enabled(1) or Disabled (0)"
    ::= {psRelay2Masks 189}

r2VBV31Alarm OBJECT-TYPE
    SYNTAX   INTEGER{disabled(0), enabled(1)}
    MAX-ACCESS  read-write
    STATUS   current
    DESCRIPTION "Alarm of rectifier31 Enabled(1) or Disabled (0)"
    ::= {psRelay2Masks 190}

r2VBV32Alarm OBJECT-TYPE
    SYNTAX   INTEGER{disabled(0), enabled(1)}
    MAX-ACCESS  read-write
    STATUS   current
    DESCRIPTION "Alarm of rectifier32 Enabled(1) or Disabled (0)"
    ::= {psRelay2Masks 191}

r2VBV33Alarm OBJECT-TYPE
    SYNTAX   INTEGER{disabled(0), enabled(1)}
    MAX-ACCESS  read-write
    STATUS   current
    DESCRIPTION "Alarm of rectifier33 Enabled(1) or Disabled (0)"
    ::= {psRelay2Masks 192}

r2VBV34Alarm OBJECT-TYPE
    SYNTAX   INTEGER{disabled(0), enabled(1)}
    MAX-ACCESS  read-write
    STATUS   current
    DESCRIPTION "Alarm of rectifier34 Enabled(1) or Disabled (0)"
    ::= {psRelay2Masks 193}

r2VBV35Alarm OBJECT-TYPE
    SYNTAX   INTEGER{disabled(0), enabled(1)}
    MAX-ACCESS  read-write
    STATUS   current
    DESCRIPTION "Alarm of rectifier35 Enabled(1) or Disabled (0)"
    ::= {psRelay2Masks 194}

r2VBV36Alarm OBJECT-TYPE
    SYNTAX   INTEGER{disabled(0), enabled(1)}
    MAX-ACCESS  read-write
    STATUS   current
    DESCRIPTION "Alarm of rectifier36 Enabled(1) or Disabled (0)"
    ::= {psRelay2Masks 195}

r2VBV37Alarm OBJECT-TYPE
    SYNTAX   INTEGER{disabled(0), enabled(1)}
    MAX-ACCESS  read-write
    STATUS   current
    DESCRIPTION "Alarm of rectifier37 Enabled(1) or Disabled (0)"
    ::= {psRelay2Masks 196}

r2VBV38Alarm OBJECT-TYPE
    SYNTAX   INTEGER{disabled(0), enabled(1)}
    MAX-ACCESS  read-write
    STATUS   current
    DESCRIPTION "Alarm of rectifier38 Enabled(1) or Disabled (0)"
    ::= {psRelay2Masks 197}

r2VBV39Alarm OBJECT-TYPE
    SYNTAX   INTEGER{disabled(0), enabled(1)}
    MAX-ACCESS  read-write
    STATUS   current
    DESCRIPTION "Alarm of rectifier39 Enabled(1) or Disabled (0)"
    ::= {psRelay2Masks 198}

r2VBV40Alarm OBJECT-TYPE
    SYNTAX   INTEGER{disabled(0), enabled(1)}
    MAX-ACCESS  read-write
    STATUS   current
    DESCRIPTION "Alarm of rectifier40 Enabled(1) or Disabled (0)"
    ::= {psRelay2Masks 199}

r2VBV41Alarm OBJECT-TYPE
    SYNTAX   INTEGER{disabled(0), enabled(1)}
    MAX-ACCESS  read-write
    STATUS   current
    DESCRIPTION "Alarm of rectifier41 Enabled(1) or Disabled (0)"
    ::= {psRelay2Masks 200}

r2VBV42Alarm OBJECT-TYPE
    SYNTAX   INTEGER{disabled(0), enabled(1)}
    MAX-ACCESS  read-write
    STATUS   current
    DESCRIPTION "Alarm of rectifier42 Enabled(1) or Disabled (0)"
    ::= {psRelay2Masks 201}

r2VBV43Alarm OBJECT-TYPE
    SYNTAX   INTEGER{disabled(0), enabled(1)}
    MAX-ACCESS  read-write
    STATUS   current
    DESCRIPTION "Alarm of rectifier43 Enabled(1) or Disabled (0)"
    ::= {psRelay2Masks 202}

r2VBV44Alarm OBJECT-TYPE
    SYNTAX   INTEGER{disabled(0), enabled(1)}
    MAX-ACCESS  read-write
    STATUS   current
    DESCRIPTION "Alarm of rectifier44 Enabled(1) or Disabled (0)"
    ::= {psRelay2Masks 203}

r2VBV45Alarm OBJECT-TYPE
    SYNTAX   INTEGER{disabled(0), enabled(1)}
    MAX-ACCESS  read-write
    STATUS   current
    DESCRIPTION "Alarm of rectifier45 Enabled(1) or Disabled (0)"
    ::= {psRelay2Masks 204}

r2VBV46Alarm OBJECT-TYPE
    SYNTAX   INTEGER{disabled(0), enabled(1)}
    MAX-ACCESS  read-write
    STATUS   current
    DESCRIPTION "Alarm of rectifier46 Enabled(1) or Disabled (0)"
    ::= {psRelay2Masks 205}

r2VBV47Alarm OBJECT-TYPE
    SYNTAX   INTEGER{disabled(0), enabled(1)}
    MAX-ACCESS  read-write
    STATUS   current
    DESCRIPTION "Alarm of rectifier47 Enabled(1) or Disabled (0)"
    ::= {psRelay2Masks 206}

r2VBV48Alarm OBJECT-TYPE
    SYNTAX   INTEGER{disabled(0), enabled(1)}
    MAX-ACCESS  read-write
    STATUS   current
    DESCRIPTION "Alarm of rectifier48 Enabled(1) or Disabled (0)"
    ::= {psRelay2Masks 207}

r2VBV49Alarm OBJECT-TYPE
    SYNTAX   INTEGER{disabled(0), enabled(1)}
    MAX-ACCESS  read-write
    STATUS   current
    DESCRIPTION "Alarm of rectifier49 Enabled(1) or Disabled (0)"
    ::= {psRelay2Masks 208}

r2VBV50Alarm OBJECT-TYPE
    SYNTAX   INTEGER{disabled(0), enabled(1)}
    MAX-ACCESS  read-write
    STATUS   current
    DESCRIPTION "Alarm of rectifier50 Enabled(1) or Disabled (0)"
    ::= {psRelay2Masks 209}

r2VBV51Alarm OBJECT-TYPE
    SYNTAX   INTEGER{disabled(0), enabled(1)}
    MAX-ACCESS  read-write
    STATUS   current
    DESCRIPTION "Alarm of rectifier51 Enabled(1) or Disabled (0)"
    ::= {psRelay2Masks 210}

r2VBV52Alarm OBJECT-TYPE
    SYNTAX   INTEGER{disabled(0), enabled(1)}
    MAX-ACCESS  read-write
    STATUS   current
    DESCRIPTION "Alarm of rectifier52 Enabled(1) or Disabled (0)"
    ::= {psRelay2Masks 211}

r2VBV53Alarm OBJECT-TYPE
    SYNTAX   INTEGER{disabled(0), enabled(1)}
    MAX-ACCESS  read-write
    STATUS   current
    DESCRIPTION "Alarm of rectifier53 Enabled(1) or Disabled (0)"
    ::= {psRelay2Masks 212}

r2VBV54Alarm OBJECT-TYPE
    SYNTAX   INTEGER{disabled(0), enabled(1)}
    MAX-ACCESS  read-write
    STATUS   current
    DESCRIPTION "Alarm of rectifier54 Enabled(1) or Disabled (0)"
    ::= {psRelay2Masks 213}

r2VBV55Alarm OBJECT-TYPE
    SYNTAX   INTEGER{disabled(0), enabled(1)}
    MAX-ACCESS  read-write
    STATUS   current
    DESCRIPTION "Alarm of rectifier55 Enabled(1) or Disabled (0)"
    ::= {psRelay2Masks 214}

r2VBV56Alarm OBJECT-TYPE
    SYNTAX   INTEGER{disabled(0), enabled(1)}
    MAX-ACCESS  read-write
    STATUS   current
    DESCRIPTION "Alarm of rectifier56 Enabled(1) or Disabled (0)"
    ::= {psRelay2Masks 215}

r2VBV57Alarm OBJECT-TYPE
    SYNTAX   INTEGER{disabled(0), enabled(1)}
    MAX-ACCESS  read-write
    STATUS   current
    DESCRIPTION "Alarm of rectifier57 Enabled(1) or Disabled (0)"
    ::= {psRelay2Masks 216}

r2VBV58Alarm OBJECT-TYPE
    SYNTAX   INTEGER{disabled(0), enabled(1)}
    MAX-ACCESS  read-write
    STATUS   current
    DESCRIPTION "Alarm of rectifier58 Enabled(1) or Disabled (0)"
    ::= {psRelay2Masks 217}

r2VBV59Alarm OBJECT-TYPE
    SYNTAX   INTEGER{disabled(0), enabled(1)}
    MAX-ACCESS  read-write
    STATUS   current
    DESCRIPTION "Alarm of rectifier59 Enabled(1) or Disabled (0)"
    ::= {psRelay2Masks 218}

r2VBV60Alarm OBJECT-TYPE
    SYNTAX   INTEGER{disabled(0), enabled(1)}
    MAX-ACCESS  read-write
    STATUS   current
    DESCRIPTION "Alarm of rectifier60 Enabled(1) or Disabled (0)"
    ::= {psRelay2Masks 219}

r2VBV61Alarm OBJECT-TYPE
    SYNTAX   INTEGER{disabled(0), enabled(1)}
    MAX-ACCESS  read-write
    STATUS   current
    DESCRIPTION "Alarm of rectifier61 Enabled(1) or Disabled (0)"
    ::= {psRelay2Masks 220}

r2VBV62Alarm OBJECT-TYPE
    SYNTAX   INTEGER{disabled(0), enabled(1)}
    MAX-ACCESS  read-write
    STATUS   current
    DESCRIPTION "Alarm of rectifier62 Enabled(1) or Disabled (0)"
    ::= {psRelay2Masks 221}

r2VBV63Alarm OBJECT-TYPE
    SYNTAX   INTEGER{disabled(0), enabled(1)}
    MAX-ACCESS  read-write
    STATUS   current
    DESCRIPTION "Alarm of rectifier63 Enabled(1) or Disabled (0)"
    ::= {psRelay2Masks 222}

r2VBV64Alarm OBJECT-TYPE
    SYNTAX   INTEGER{disabled(0), enabled(1)}
    MAX-ACCESS  read-write
    STATUS   current
    DESCRIPTION "Alarm of rectifier64 Enabled(1) or Disabled (0)"
    ::= {psRelay2Masks 223}

r2VBV65Alarm OBJECT-TYPE
    SYNTAX   INTEGER{disabled(0), enabled(1)}
    MAX-ACCESS  read-write
    STATUS   current
    DESCRIPTION "Alarm of rectifier65 Enabled(1) or Disabled (0)"
    ::= {psRelay2Masks 224}

r2VBV66Alarm OBJECT-TYPE
    SYNTAX   INTEGER{disabled(0), enabled(1)}
    MAX-ACCESS  read-write
    STATUS   current
    DESCRIPTION "Alarm of rectifier66 Enabled(1) or Disabled (0)"
    ::= {psRelay2Masks 225}

r2VBV67Alarm OBJECT-TYPE
    SYNTAX   INTEGER{disabled(0), enabled(1)}
    MAX-ACCESS  read-write
    STATUS   current
    DESCRIPTION "Alarm of rectifier67 Enabled(1) or Disabled (0)"
    ::= {psRelay2Masks 226}

r2VBV68Alarm OBJECT-TYPE
    SYNTAX   INTEGER{disabled(0), enabled(1)}
    MAX-ACCESS  read-write
    STATUS   current
    DESCRIPTION "Alarm of rectifier68 Enabled(1) or Disabled (0)"
    ::= {psRelay2Masks 227}

r2VBV69Alarm OBJECT-TYPE
    SYNTAX   INTEGER{disabled(0), enabled(1)}
    MAX-ACCESS  read-write
    STATUS   current
    DESCRIPTION "Alarm of rectifier69 Enabled(1) or Disabled (0)"
    ::= {psRelay2Masks 228}

r2VBV70Alarm OBJECT-TYPE
    SYNTAX   INTEGER{disabled(0), enabled(1)}
    MAX-ACCESS  read-write
    STATUS   current
    DESCRIPTION "Alarm of rectifier70 Enabled(1) or Disabled (0)"
    ::= {psRelay2Masks 229}

r2VBV71Alarm OBJECT-TYPE
    SYNTAX   INTEGER{disabled(0), enabled(1)}
    MAX-ACCESS  read-write
    STATUS   current
    DESCRIPTION "Alarm of rectifier71 Enabled(1) or Disabled (0)"
    ::= {psRelay2Masks 230}

r2VBV72Alarm OBJECT-TYPE
    SYNTAX   INTEGER{disabled(0), enabled(1)}
    MAX-ACCESS  read-write
    STATUS   current
    DESCRIPTION "Alarm of rectifier72 Enabled(1) or Disabled (0)"
    ::= {psRelay2Masks 231}

r2VBV73Alarm OBJECT-TYPE
    SYNTAX   INTEGER{disabled(0), enabled(1)}
    MAX-ACCESS  read-write
    STATUS   current
    DESCRIPTION "Alarm of rectifier73 Enabled(1) or Disabled (0)"
    ::= {psRelay2Masks 232}

r2VBV74Alarm OBJECT-TYPE
    SYNTAX   INTEGER{disabled(0), enabled(1)}
    MAX-ACCESS  read-write
    STATUS   current
    DESCRIPTION "Alarm of rectifier74 Enabled(1) or Disabled (0)"
    ::= {psRelay2Masks 233}

r2VBV75Alarm OBJECT-TYPE
    SYNTAX   INTEGER{disabled(0), enabled(1)}
    MAX-ACCESS  read-write
    STATUS   current
    DESCRIPTION "Alarm of rectifier75 Enabled(1) or Disabled (0)"
    ::= {psRelay2Masks 234}

r2VBV76Alarm OBJECT-TYPE
    SYNTAX   INTEGER{disabled(0), enabled(1)}
    MAX-ACCESS  read-write
    STATUS   current
    DESCRIPTION "Alarm of rectifier76 Enabled(1) or Disabled (0)"
    ::= {psRelay2Masks 235}

r2VBV77Alarm OBJECT-TYPE
    SYNTAX   INTEGER{disabled(0), enabled(1)}
    MAX-ACCESS  read-write
    STATUS   current
    DESCRIPTION "Alarm of rectifier77 Enabled(1) or Disabled (0)"
    ::= {psRelay2Masks 236}

r2VBV78Alarm OBJECT-TYPE
    SYNTAX   INTEGER{disabled(0), enabled(1)}
    MAX-ACCESS  read-write
    STATUS   current
    DESCRIPTION "Alarm of rectifier78 Enabled(1) or Disabled (0)"
    ::= {psRelay2Masks 237}

r2VBV79Alarm OBJECT-TYPE
    SYNTAX   INTEGER{disabled(0), enabled(1)}
    MAX-ACCESS  read-write
    STATUS   current
    DESCRIPTION "Alarm of rectifier79 Enabled(1) or Disabled (0)"
    ::= {psRelay2Masks 238}

r2VBV80Alarm OBJECT-TYPE
    SYNTAX   INTEGER{disabled(0), enabled(1)}
    MAX-ACCESS  read-write
    STATUS   current
    DESCRIPTION "Alarm of rectifier80 Enabled(1) or Disabled (0)"
    ::= {psRelay2Masks 239}

r2VBV81Alarm OBJECT-TYPE
    SYNTAX   INTEGER{disabled(0), enabled(1)}
    MAX-ACCESS  read-write
    STATUS   current
    DESCRIPTION "Alarm of rectifier81 Enabled(1) or Disabled (0)"
    ::= {psRelay2Masks 240}

r2VBV82Alarm OBJECT-TYPE
    SYNTAX   INTEGER{disabled(0), enabled(1)}
    MAX-ACCESS  read-write
    STATUS   current
    DESCRIPTION "Alarm of rectifier82 Enabled(1) or Disabled (0)"
    ::= {psRelay2Masks 241}

r2VBV83Alarm OBJECT-TYPE
    SYNTAX   INTEGER{disabled(0), enabled(1)}
    MAX-ACCESS  read-write
    STATUS   current
    DESCRIPTION "Alarm of rectifier83 Enabled(1) or Disabled (0)"
    ::= {psRelay2Masks 242}

r2VBV84Alarm OBJECT-TYPE
    SYNTAX   INTEGER{disabled(0), enabled(1)}
    MAX-ACCESS  read-write
    STATUS   current
    DESCRIPTION "Alarm of rectifier84 Enabled(1) or Disabled (0)"
    ::= {psRelay2Masks 243}

r2VBV85Alarm OBJECT-TYPE
    SYNTAX   INTEGER{disabled(0), enabled(1)}
    MAX-ACCESS  read-write
    STATUS   current
    DESCRIPTION "Alarm of rectifier85 Enabled(1) or Disabled (0)"
    ::= {psRelay2Masks 244}

r2VBV86Alarm OBJECT-TYPE
    SYNTAX   INTEGER{disabled(0), enabled(1)}
    MAX-ACCESS  read-write
    STATUS   current
    DESCRIPTION "Alarm of rectifier86 Enabled(1) or Disabled (0)"
    ::= {psRelay2Masks 245}

r2VBV87Alarm OBJECT-TYPE
    SYNTAX   INTEGER{disabled(0), enabled(1)}
    MAX-ACCESS  read-write
    STATUS   current
    DESCRIPTION "Alarm of rectifier87 Enabled(1) or Disabled (0)"
    ::= {psRelay2Masks 246}

r2VBV88Alarm OBJECT-TYPE
    SYNTAX   INTEGER{disabled(0), enabled(1)}
    MAX-ACCESS  read-write
    STATUS   current
    DESCRIPTION "Alarm of rectifier88 Enabled(1) or Disabled (0)"
    ::= {psRelay2Masks 247}

r2VBV89Alarm OBJECT-TYPE
    SYNTAX   INTEGER{disabled(0), enabled(1)}
    MAX-ACCESS  read-write
    STATUS   current
    DESCRIPTION "Alarm of rectifier89 Enabled(1) or Disabled (0)"
    ::= {psRelay2Masks 248}

r2VBV90Alarm OBJECT-TYPE
    SYNTAX   INTEGER{disabled(0), enabled(1)}
    MAX-ACCESS  read-write
    STATUS   current
    DESCRIPTION "Alarm of rectifier90 Enabled(1) or Disabled (0)"
    ::= {psRelay2Masks 249}

r2VBV91Alarm OBJECT-TYPE
    SYNTAX   INTEGER{disabled(0), enabled(1)}
    MAX-ACCESS  read-write
    STATUS   current
    DESCRIPTION "Alarm of rectifier91 Enabled(1) or Disabled (0)"
    ::= {psRelay2Masks 250}

r2VBV92Alarm OBJECT-TYPE
    SYNTAX   INTEGER{disabled(0), enabled(1)}
    MAX-ACCESS  read-write
    STATUS   current
    DESCRIPTION "Alarm of rectifier92 Enabled(1) or Disabled (0)"
    ::= {psRelay2Masks 251}

r2VBV93Alarm OBJECT-TYPE
    SYNTAX   INTEGER{disabled(0), enabled(1)}
    MAX-ACCESS  read-write
    STATUS   current
    DESCRIPTION "Alarm of rectifier93 Enabled(1) or Disabled (0)"
    ::= {psRelay2Masks 252}

r2VBV94Alarm OBJECT-TYPE
    SYNTAX   INTEGER{disabled(0), enabled(1)}
    MAX-ACCESS  read-write
    STATUS   current
    DESCRIPTION "Alarm of rectifier94 Enabled(1) or Disabled (0)"
    ::= {psRelay2Masks 253}

r2VBV95Alarm OBJECT-TYPE
    SYNTAX   INTEGER{disabled(0), enabled(1)}
    MAX-ACCESS  read-write
    STATUS   current
    DESCRIPTION "Alarm of rectifier95 Enabled(1) or Disabled (0)"
    ::= {psRelay2Masks 254}

r2VBV96Alarm OBJECT-TYPE
    SYNTAX   INTEGER{disabled(0), enabled(1)}
    MAX-ACCESS  read-write
    STATUS   current
    DESCRIPTION "Alarm of rectifier96 Enabled(1) or Disabled (0)"
    ::= {psRelay2Masks 255}

r2VBV97Alarm OBJECT-TYPE
    SYNTAX   INTEGER{disabled(0), enabled(1)}
    MAX-ACCESS  read-write
    STATUS   current
    DESCRIPTION "Alarm of rectifier97 Enabled(1) or Disabled (0)"
    ::= {psRelay2Masks 256}

r2VBV98Alarm OBJECT-TYPE
    SYNTAX   INTEGER{disabled(0), enabled(1)}
    MAX-ACCESS  read-write
    STATUS   current
    DESCRIPTION "Alarm of rectifier98 Enabled(1) or Disabled (0)"
    ::= {psRelay2Masks 257}

r2VBV99Alarm OBJECT-TYPE
    SYNTAX   INTEGER{disabled(0), enabled(1)}
    MAX-ACCESS  read-write
    STATUS   current
    DESCRIPTION "Alarm of rectifier99 Enabled(1) or Disabled (0)"
    ::= {psRelay2Masks 258}

r2VBV100Alarm OBJECT-TYPE
    SYNTAX   INTEGER{disabled(0), enabled(1)}
    MAX-ACCESS  read-write
    STATUS   current
    DESCRIPTION "Alarm of rectifier100 Enabled(1) or Disabled (0)"
    ::= {psRelay2Masks 259}

r2VBV101Alarm OBJECT-TYPE
    SYNTAX   INTEGER{disabled(0), enabled(1)}
    MAX-ACCESS  read-write
    STATUS   current
    DESCRIPTION "Alarm of rectifier101 Enabled(1) or Disabled (0)"
    ::= {psRelay2Masks 260}

r2VBV102Alarm OBJECT-TYPE
    SYNTAX   INTEGER{disabled(0), enabled(1)}
    MAX-ACCESS  read-write
    STATUS   current
    DESCRIPTION "Alarm of rectifier102 Enabled(1) or Disabled (0)"
    ::= {psRelay2Masks 261}

r2VBV103Alarm OBJECT-TYPE
    SYNTAX   INTEGER{disabled(0), enabled(1)}
    MAX-ACCESS  read-write
    STATUS   current
    DESCRIPTION "Alarm of rectifier103 Enabled(1) or Disabled (0)"
    ::= {psRelay2Masks 262}

r2VBV104Alarm OBJECT-TYPE
    SYNTAX   INTEGER{disabled(0), enabled(1)}
    MAX-ACCESS  read-write
    STATUS   current
    DESCRIPTION "Alarm of rectifier104 Enabled(1) or Disabled (0)"
    ::= {psRelay2Masks 263}

r2VBV105Alarm OBJECT-TYPE
    SYNTAX   INTEGER{disabled(0), enabled(1)}
    MAX-ACCESS  read-write
    STATUS   current
    DESCRIPTION "Alarm of rectifier105 Enabled(1) or Disabled (0)"
    ::= {psRelay2Masks 264}

r2VBV106Alarm OBJECT-TYPE
    SYNTAX   INTEGER{disabled(0), enabled(1)}
    MAX-ACCESS  read-write
    STATUS   current
    DESCRIPTION "Alarm of rectifier106 Enabled(1) or Disabled (0)"
    ::= {psRelay2Masks 265}

r2VBV107Alarm OBJECT-TYPE
    SYNTAX   INTEGER{disabled(0), enabled(1)}
    MAX-ACCESS  read-write
    STATUS   current
    DESCRIPTION "Alarm of rectifier107 Enabled(1) or Disabled (0)"
    ::= {psRelay2Masks 266}

r2VBV108Alarm OBJECT-TYPE
    SYNTAX   INTEGER{disabled(0), enabled(1)}
    MAX-ACCESS  read-write
    STATUS   current
    DESCRIPTION "Alarm of rectifier108 Enabled(1) or Disabled (0)"
    ::= {psRelay2Masks 267}

r2VBV109Alarm OBJECT-TYPE
    SYNTAX   INTEGER{disabled(0), enabled(1)}
    MAX-ACCESS  read-write
    STATUS   current
    DESCRIPTION "Alarm of rectifier109 Enabled(1) or Disabled (0)"
    ::= {psRelay2Masks 268}

r2VBV110Alarm OBJECT-TYPE
    SYNTAX   INTEGER{disabled(0), enabled(1)}
    MAX-ACCESS  read-write
    STATUS   current
    DESCRIPTION "Alarm of rectifier110 Enabled(1) or Disabled (0)"
    ::= {psRelay2Masks 269}

r2VBV111Alarm OBJECT-TYPE
    SYNTAX   INTEGER{disabled(0), enabled(1)}
    MAX-ACCESS  read-write
    STATUS   current
    DESCRIPTION "Alarm of rectifier111 Enabled(1) or Disabled (0)"
    ::= {psRelay2Masks 270}

r2VBV112Alarm OBJECT-TYPE
    SYNTAX   INTEGER{disabled(0), enabled(1)}
    MAX-ACCESS  read-write
    STATUS   current
    DESCRIPTION "Alarm of rectifier112 Enabled(1) or Disabled (0)"
    ::= {psRelay2Masks 271}

r2VBV113Alarm OBJECT-TYPE
    SYNTAX   INTEGER{disabled(0), enabled(1)}
    MAX-ACCESS  read-write
    STATUS   current
    DESCRIPTION "Alarm of rectifier113 Enabled(1) or Disabled (0)"
    ::= {psRelay2Masks 272}

r2VBV114Alarm OBJECT-TYPE
    SYNTAX   INTEGER{disabled(0), enabled(1)}
    MAX-ACCESS  read-write
    STATUS   current
    DESCRIPTION "Alarm of rectifier114 Enabled(1) or Disabled (0)"
    ::= {psRelay2Masks 273}

r2VBV115Alarm OBJECT-TYPE
    SYNTAX   INTEGER{disabled(0), enabled(1)}
    MAX-ACCESS  read-write
    STATUS   current
    DESCRIPTION "Alarm of rectifier115 Enabled(1) or Disabled (0)"
    ::= {psRelay2Masks 274}

r2VBV116Alarm OBJECT-TYPE
    SYNTAX   INTEGER{disabled(0), enabled(1)}
    MAX-ACCESS  read-write
    STATUS   current
    DESCRIPTION "Alarm of rectifier116 Enabled(1) or Disabled (0)"
    ::= {psRelay2Masks 275}

r2VBV117Alarm OBJECT-TYPE
    SYNTAX   INTEGER{disabled(0), enabled(1)}
    MAX-ACCESS  read-write
    STATUS   current
    DESCRIPTION "Alarm of rectifier117 Enabled(1) or Disabled (0)"
    ::= {psRelay2Masks 276}

r2VBV118Alarm OBJECT-TYPE
    SYNTAX   INTEGER{disabled(0), enabled(1)}
    MAX-ACCESS  read-write
    STATUS   current
    DESCRIPTION "Alarm of rectifier118 Enabled(1) or Disabled (0)"
    ::= {psRelay2Masks 277}

r2VBV119Alarm OBJECT-TYPE
    SYNTAX   INTEGER{disabled(0), enabled(1)}
    MAX-ACCESS  read-write
    STATUS   current
    DESCRIPTION "Alarm of rectifier119 Enabled(1) or Disabled (0)"
    ::= {psRelay2Masks 278}

r2VBV120Alarm OBJECT-TYPE
    SYNTAX   INTEGER{disabled(0), enabled(1)}
    MAX-ACCESS  read-write
    STATUS   current
    DESCRIPTION "Alarm of rectifier120 Enabled(1) or Disabled (0)"
    ::= {psRelay2Masks 279}

r2VBV121Alarm OBJECT-TYPE
    SYNTAX   INTEGER{disabled(0), enabled(1)}
    MAX-ACCESS  read-write
    STATUS   current
    DESCRIPTION "Alarm of rectifier121 Enabled(1) or Disabled (0)"
    ::= {psRelay2Masks 280}

r2VBV122Alarm OBJECT-TYPE
    SYNTAX   INTEGER{disabled(0), enabled(1)}
    MAX-ACCESS  read-write
    STATUS   current
    DESCRIPTION "Alarm of rectifier122 Enabled(1) or Disabled (0)"
    ::= {psRelay2Masks 281}

r2VBV123Alarm OBJECT-TYPE
    SYNTAX   INTEGER{disabled(0), enabled(1)}
    MAX-ACCESS  read-write
    STATUS   current
    DESCRIPTION "Alarm of rectifier123 Enabled(1) or Disabled (0)"
    ::= {psRelay2Masks 282}

r2VBV124Alarm OBJECT-TYPE
    SYNTAX   INTEGER{disabled(0), enabled(1)}
    MAX-ACCESS  read-write
    STATUS   current
    DESCRIPTION "Alarm of rectifier124 Enabled(1) or Disabled (0)"
    ::= {psRelay2Masks 283}

r2VBV125Alarm OBJECT-TYPE
    SYNTAX   INTEGER{disabled(0), enabled(1)}
    MAX-ACCESS  read-write
    STATUS   current
    DESCRIPTION "Alarm of rectifier125 Enabled(1) or Disabled (0)"
    ::= {psRelay2Masks 284}

r2VBV126Alarm OBJECT-TYPE
    SYNTAX   INTEGER{disabled(0), enabled(1)}
    MAX-ACCESS  read-write
    STATUS   current
    DESCRIPTION "Alarm of rectifier126 Enabled(1) or Disabled (0)"
    ::= {psRelay2Masks 285}

r2VBV127Alarm OBJECT-TYPE
    SYNTAX   INTEGER{disabled(0), enabled(1)}
    MAX-ACCESS  read-write
    STATUS   current
    DESCRIPTION "Alarm of rectifier127 Enabled(1) or Disabled (0)"
    ::= {psRelay2Masks 286}

r2VBV128Alarm OBJECT-TYPE
    SYNTAX   INTEGER{disabled(0), enabled(1)}
    MAX-ACCESS  read-write
    STATUS   current
    DESCRIPTION "Alarm of rectifier128 Enabled(1) or Disabled (0)"
    ::= {psRelay2Masks 287}

r2VBV129Alarm OBJECT-TYPE
    SYNTAX   INTEGER{disabled(0), enabled(1)}
    MAX-ACCESS  read-write
    STATUS   current
    DESCRIPTION "Alarm of rectifier129 Enabled(1) or Disabled (0)"
    ::= {psRelay2Masks 288}

r2VBV130Alarm OBJECT-TYPE
    SYNTAX   INTEGER{disabled(0), enabled(1)}
    MAX-ACCESS  read-write
    STATUS   current
    DESCRIPTION "Alarm of rectifier130 Enabled(1) or Disabled (0)"
    ::= {psRelay2Masks 289}

r2VBV131Alarm OBJECT-TYPE
    SYNTAX   INTEGER{disabled(0), enabled(1)}
    MAX-ACCESS  read-write
    STATUS   current
    DESCRIPTION "Alarm of rectifier131 Enabled(1) or Disabled (0)"
    ::= {psRelay2Masks 290}

r2VBV132Alarm OBJECT-TYPE
    SYNTAX   INTEGER{disabled(0), enabled(1)}
    MAX-ACCESS  read-write
    STATUS   current
    DESCRIPTION "Alarm of rectifier132 Enabled(1) or Disabled (0)"
    ::= {psRelay2Masks 291}

r2VBV133Alarm OBJECT-TYPE
    SYNTAX   INTEGER{disabled(0), enabled(1)}
    MAX-ACCESS  read-write
    STATUS   current
    DESCRIPTION "Alarm of rectifier133 Enabled(1) or Disabled (0)"
    ::= {psRelay2Masks 292}

r2VBV134Alarm OBJECT-TYPE
    SYNTAX   INTEGER{disabled(0), enabled(1)}
    MAX-ACCESS  read-write
    STATUS   current
    DESCRIPTION "Alarm of rectifier134 Enabled(1) or Disabled (0)"
    ::= {psRelay2Masks 293}

r2VBV135Alarm OBJECT-TYPE
    SYNTAX   INTEGER{disabled(0), enabled(1)}
    MAX-ACCESS  read-write
    STATUS   current
    DESCRIPTION "Alarm of rectifier135 Enabled(1) or Disabled (0)"
    ::= {psRelay2Masks 294}

r2VBV136Alarm OBJECT-TYPE
    SYNTAX   INTEGER{disabled(0), enabled(1)}
    MAX-ACCESS  read-write
    STATUS   current
    DESCRIPTION "Alarm of rectifier136 Enabled(1) or Disabled (0)"
    ::= {psRelay2Masks 295}

r2VBV137Alarm OBJECT-TYPE
    SYNTAX   INTEGER{disabled(0), enabled(1)}
    MAX-ACCESS  read-write
    STATUS   current
    DESCRIPTION "Alarm of rectifier137 Enabled(1) or Disabled (0)"
    ::= {psRelay2Masks 296}

r2VBV138Alarm OBJECT-TYPE
    SYNTAX   INTEGER{disabled(0), enabled(1)}
    MAX-ACCESS  read-write
    STATUS   current
    DESCRIPTION "Alarm of rectifier138 Enabled(1) or Disabled (0)"
    ::= {psRelay2Masks 297}

r2VBV139Alarm OBJECT-TYPE
    SYNTAX   INTEGER{disabled(0), enabled(1)}
    MAX-ACCESS  read-write
    STATUS   current
    DESCRIPTION "Alarm of rectifier139 Enabled(1) or Disabled (0)"
    ::= {psRelay2Masks 298}

r2VBV140Alarm OBJECT-TYPE
    SYNTAX   INTEGER{disabled(0), enabled(1)}
    MAX-ACCESS  read-write
    STATUS   current
    DESCRIPTION "Alarm of rectifier140 Enabled(1) or Disabled (0)"
    ::= {psRelay2Masks 299}

r2VBV141Alarm OBJECT-TYPE
    SYNTAX   INTEGER{disabled(0), enabled(1)}
    MAX-ACCESS  read-write
    STATUS   current
    DESCRIPTION "Alarm of rectifier141 Enabled(1) or Disabled (0)"
    ::= {psRelay2Masks 300}

r2VBV142Alarm OBJECT-TYPE
    SYNTAX   INTEGER{disabled(0), enabled(1)}
    MAX-ACCESS  read-write
    STATUS   current
    DESCRIPTION "Alarm of rectifier142 Enabled(1) or Disabled (0)"
    ::= {psRelay2Masks 301}

r2VBV143Alarm OBJECT-TYPE
    SYNTAX   INTEGER{disabled(0), enabled(1)}
    MAX-ACCESS  read-write
    STATUS   current
    DESCRIPTION "Alarm of rectifier143 Enabled(1) or Disabled (0)"
    ::= {psRelay2Masks 302}

r2VBV144Alarm OBJECT-TYPE
    SYNTAX   INTEGER{disabled(0), enabled(1)}
    MAX-ACCESS  read-write
    STATUS   current
    DESCRIPTION "Alarm of rectifier144 Enabled(1) or Disabled (0)"
    ::= {psRelay2Masks 303}

r2VBV145Alarm OBJECT-TYPE
    SYNTAX   INTEGER{disabled(0), enabled(1)}
    MAX-ACCESS  read-write
    STATUS   current
    DESCRIPTION "Alarm of rectifier145 Enabled(1) or Disabled (0)"
    ::= {psRelay2Masks 304}

r2VBV146Alarm OBJECT-TYPE
    SYNTAX   INTEGER{disabled(0), enabled(1)}
    MAX-ACCESS  read-write
    STATUS   current
    DESCRIPTION "Alarm of rectifier146 Enabled(1) or Disabled (0)"
    ::= {psRelay2Masks 305}

r2VBV147Alarm OBJECT-TYPE
    SYNTAX   INTEGER{disabled(0), enabled(1)}
    MAX-ACCESS  read-write
    STATUS   current
    DESCRIPTION "Alarm of rectifier147 Enabled(1) or Disabled (0)"
    ::= {psRelay2Masks 306}

r2VBV148Alarm OBJECT-TYPE
    SYNTAX   INTEGER{disabled(0), enabled(1)}
    MAX-ACCESS  read-write
    STATUS   current
    DESCRIPTION "Alarm of rectifier148 Enabled(1) or Disabled (0)"
    ::= {psRelay2Masks 307}

r2VBV149Alarm OBJECT-TYPE
    SYNTAX   INTEGER{disabled(0), enabled(1)}
    MAX-ACCESS  read-write
    STATUS   current
    DESCRIPTION "Alarm of rectifier149 Enabled(1) or Disabled (0)"
    ::= {psRelay2Masks 308}

r2VBV150Alarm OBJECT-TYPE
    SYNTAX   INTEGER{disabled(0), enabled(1)}
    MAX-ACCESS  read-write
    STATUS   current
    DESCRIPTION "Alarm of rectifier150 Enabled(1) or Disabled (0)"
    ::= {psRelay2Masks 309}

r2VBV151Alarm OBJECT-TYPE
    SYNTAX   INTEGER{disabled(0), enabled(1)}
    MAX-ACCESS  read-write
    STATUS   current
    DESCRIPTION "Alarm of rectifier151 Enabled(1) or Disabled (0)"
    ::= {psRelay2Masks 310}

r2VBV152Alarm OBJECT-TYPE
    SYNTAX   INTEGER{disabled(0), enabled(1)}
    MAX-ACCESS  read-write
    STATUS   current
    DESCRIPTION "Alarm of rectifier152 Enabled(1) or Disabled (0)"
    ::= {psRelay2Masks 311}

r2VBV153Alarm OBJECT-TYPE
    SYNTAX   INTEGER{disabled(0), enabled(1)}
    MAX-ACCESS  read-write
    STATUS   current
    DESCRIPTION "Alarm of rectifier153 Enabled(1) or Disabled (0)"
    ::= {psRelay2Masks 312}

r2VBV154Alarm OBJECT-TYPE
    SYNTAX   INTEGER{disabled(0), enabled(1)}
    MAX-ACCESS  read-write
    STATUS   current
    DESCRIPTION "Alarm of rectifier154 Enabled(1) or Disabled (0)"
    ::= {psRelay2Masks 313}

r2VBV155Alarm OBJECT-TYPE
    SYNTAX   INTEGER{disabled(0), enabled(1)}
    MAX-ACCESS  read-write
    STATUS   current
    DESCRIPTION "Alarm of rectifier155 Enabled(1) or Disabled (0)"
    ::= {psRelay2Masks 314}

r2VBV156Alarm OBJECT-TYPE
    SYNTAX   INTEGER{disabled(0), enabled(1)}
    MAX-ACCESS  read-write
    STATUS   current
    DESCRIPTION "Alarm of rectifier156 Enabled(1) or Disabled (0)"
    ::= {psRelay2Masks 315}

r2VBV157Alarm OBJECT-TYPE
    SYNTAX   INTEGER{disabled(0), enabled(1)}
    MAX-ACCESS  read-write
    STATUS   current
    DESCRIPTION "Alarm of rectifier157 Enabled(1) or Disabled (0)"
    ::= {psRelay2Masks 316}

r2VBV158Alarm OBJECT-TYPE
    SYNTAX   INTEGER{disabled(0), enabled(1)}
    MAX-ACCESS  read-write
    STATUS   current
    DESCRIPTION "Alarm of rectifier158 Enabled(1) or Disabled (0)"
    ::= {psRelay2Masks 317}

r2VBV159Alarm OBJECT-TYPE
    SYNTAX   INTEGER{disabled(0), enabled(1)}
    MAX-ACCESS  read-write
    STATUS   current
    DESCRIPTION "Alarm of rectifier159 Enabled(1) or Disabled (0)"
    ::= {psRelay2Masks 318}

r2VBV160Alarm OBJECT-TYPE
    SYNTAX   INTEGER{disabled(0), enabled(1)}
    MAX-ACCESS  read-write
    STATUS   current
    DESCRIPTION "Alarm of rectifier160 Enabled(1) or Disabled (0)"
    ::= {psRelay2Masks 319}

r2VBV161Alarm OBJECT-TYPE
    SYNTAX   INTEGER{disabled(0), enabled(1)}
    MAX-ACCESS  read-write
    STATUS   current
    DESCRIPTION "Alarm of rectifier161 Enabled(1) or Disabled (0)"
    ::= {psRelay2Masks 320}

r2VBV162Alarm OBJECT-TYPE
    SYNTAX   INTEGER{disabled(0), enabled(1)}
    MAX-ACCESS  read-write
    STATUS   current
    DESCRIPTION "Alarm of rectifier162 Enabled(1) or Disabled (0)"
    ::= {psRelay2Masks 321}

r2VBV163Alarm OBJECT-TYPE
    SYNTAX   INTEGER{disabled(0), enabled(1)}
    MAX-ACCESS  read-write
    STATUS   current
    DESCRIPTION "Alarm of rectifier163 Enabled(1) or Disabled (0)"
    ::= {psRelay2Masks 322}

r2VBV164Alarm OBJECT-TYPE
    SYNTAX   INTEGER{disabled(0), enabled(1)}
    MAX-ACCESS  read-write
    STATUS   current
    DESCRIPTION "Alarm of rectifier164 Enabled(1) or Disabled (0)"
    ::= {psRelay2Masks 323}

r2VBV165Alarm OBJECT-TYPE
    SYNTAX   INTEGER{disabled(0), enabled(1)}
    MAX-ACCESS  read-write
    STATUS   current
    DESCRIPTION "Alarm of rectifier165 Enabled(1) or Disabled (0)"
    ::= {psRelay2Masks 324}

r2VBV166Alarm OBJECT-TYPE
    SYNTAX   INTEGER{disabled(0), enabled(1)}
    MAX-ACCESS  read-write
    STATUS   current
    DESCRIPTION "Alarm of rectifier166 Enabled(1) or Disabled (0)"
    ::= {psRelay2Masks 325}

r2VBV167Alarm OBJECT-TYPE
    SYNTAX   INTEGER{disabled(0), enabled(1)}
    MAX-ACCESS  read-write
    STATUS   current
    DESCRIPTION "Alarm of rectifier167 Enabled(1) or Disabled (0)"
    ::= {psRelay2Masks 326}

r2VBV168Alarm OBJECT-TYPE
    SYNTAX   INTEGER{disabled(0), enabled(1)}
    MAX-ACCESS  read-write
    STATUS   current
    DESCRIPTION "Alarm of rectifier168 Enabled(1) or Disabled (0)"
    ::= {psRelay2Masks 327}

r2VBV169Alarm OBJECT-TYPE
    SYNTAX   INTEGER{disabled(0), enabled(1)}
    MAX-ACCESS  read-write
    STATUS   current
    DESCRIPTION "Alarm of rectifier169 Enabled(1) or Disabled (0)"
    ::= {psRelay2Masks 328}

r2VBV170Alarm OBJECT-TYPE
    SYNTAX   INTEGER{disabled(0), enabled(1)}
    MAX-ACCESS  read-write
    STATUS   current
    DESCRIPTION "Alarm of rectifier170 Enabled(1) or Disabled (0)"
    ::= {psRelay2Masks 329}

r2VBV171Alarm OBJECT-TYPE
    SYNTAX   INTEGER{disabled(0), enabled(1)}
    MAX-ACCESS  read-write
    STATUS   current
    DESCRIPTION "Alarm of rectifier171 Enabled(1) or Disabled (0)"
    ::= {psRelay2Masks 330}

r2VBV172Alarm OBJECT-TYPE
    SYNTAX   INTEGER{disabled(0), enabled(1)}
    MAX-ACCESS  read-write
    STATUS   current
    DESCRIPTION "Alarm of rectifier172 Enabled(1) or Disabled (0)"
    ::= {psRelay2Masks 331}

r2VBV173Alarm OBJECT-TYPE
    SYNTAX   INTEGER{disabled(0), enabled(1)}
    MAX-ACCESS  read-write
    STATUS   current
    DESCRIPTION "Alarm of rectifier173 Enabled(1) or Disabled (0)"
    ::= {psRelay2Masks 332}

r2VBV174Alarm OBJECT-TYPE
    SYNTAX   INTEGER{disabled(0), enabled(1)}
    MAX-ACCESS  read-write
    STATUS   current
    DESCRIPTION "Alarm of rectifier174 Enabled(1) or Disabled (0)"
    ::= {psRelay2Masks 333}

r2VBV175Alarm OBJECT-TYPE
    SYNTAX   INTEGER{disabled(0), enabled(1)}
    MAX-ACCESS  read-write
    STATUS   current
    DESCRIPTION "Alarm of rectifier175 Enabled(1) or Disabled (0)"
    ::= {psRelay2Masks 334}

r2VBV176Alarm OBJECT-TYPE
    SYNTAX   INTEGER{disabled(0), enabled(1)}
    MAX-ACCESS  read-write
    STATUS   current
    DESCRIPTION "Alarm of rectifier176 Enabled(1) or Disabled (0)"
    ::= {psRelay2Masks 335}

r2VBV177Alarm OBJECT-TYPE
    SYNTAX   INTEGER{disabled(0), enabled(1)}
    MAX-ACCESS  read-write
    STATUS   current
    DESCRIPTION "Alarm of rectifier177 Enabled(1) or Disabled (0)"
    ::= {psRelay2Masks 336}

r2VBV178Alarm OBJECT-TYPE
    SYNTAX   INTEGER{disabled(0), enabled(1)}
    MAX-ACCESS  read-write
    STATUS   current
    DESCRIPTION "Alarm of rectifier178 Enabled(1) or Disabled (0)"
    ::= {psRelay2Masks 337}

r2VBV179Alarm OBJECT-TYPE
    SYNTAX   INTEGER{disabled(0), enabled(1)}
    MAX-ACCESS  read-write
    STATUS   current
    DESCRIPTION "Alarm of rectifier179 Enabled(1) or Disabled (0)"
    ::= {psRelay2Masks 338}

r2VBV180Alarm OBJECT-TYPE
    SYNTAX   INTEGER{disabled(0), enabled(1)}
    MAX-ACCESS  read-write
    STATUS   current
    DESCRIPTION "Alarm of rectifier180 Enabled(1) or Disabled (0)"
    ::= {psRelay2Masks 339}

r2VBVNoReserve OBJECT-TYPE
    SYNTAX   INTEGER{disabled(0), enabled(1)}
    MAX-ACCESS  read-write
    STATUS   current
    DESCRIPTION "Enabled(1) or Disabled (0)"
    ::= {psRelay2Masks 340}

r2VBVHighEfficiency OBJECT-TYPE
    SYNTAX   INTEGER{disabled(0), enabled(1)}
    MAX-ACCESS  read-write
    STATUS   current
    DESCRIPTION "Enabled(1) or Disabled (0)"
    ::= {psRelay2Masks 341}

--PhasesAlarm in psRelay2Masks
r2Phase1Alarm OBJECT-TYPE
    SYNTAX   INTEGER{disabled(0), enabled(1)}
    MAX-ACCESS  read-write
    STATUS   current
    DESCRIPTION "Enabled(1) or Disabled (0)"
    ::= {psRelay2Masks 352}

r2Phase2Alarm OBJECT-TYPE
    SYNTAX   INTEGER{disabled(0), enabled(1)}
    MAX-ACCESS  read-write
    STATUS   current
    DESCRIPTION "Enabled(1) or Disabled (0)"
    ::= {psRelay2Masks 353}

r2Phase3Alarm OBJECT-TYPE
    SYNTAX   INTEGER{disabled(0), enabled(1)}
    MAX-ACCESS  read-write
    STATUS   current
    DESCRIPTION "Enabled(1) or Disabled (0)"
    ::= {psRelay2Masks 354}

r2MainsSensorError OBJECT-TYPE
    SYNTAX   INTEGER{disabled(0), enabled(1)}
    MAX-ACCESS  read-write
    STATUS   current
    DESCRIPTION "Enabled(1) or Disabled (0)"
    ::= {psRelay2Masks 355}

r2LightProtectionAlarm OBJECT-TYPE
    SYNTAX   INTEGER{disabled(0), enabled(1)}
    MAX-ACCESS  read-write
    STATUS   current
    DESCRIPTION "Enabled(1) or Disabled (0)"
    ::= {psRelay2Masks 356}

--Ambience Temperature in psRelay2Masks
r2LowTemperature OBJECT-TYPE
    SYNTAX   INTEGER{disabled(0), enabled(1)}
    MAX-ACCESS  read-write
    STATUS   current
    DESCRIPTION "Enabled(1) or Disabled (0)"
    ::= {psRelay2Masks 384}

r2HighTemperature OBJECT-TYPE
    SYNTAX   INTEGER{disabled(0), enabled(1)}
    MAX-ACCESS  read-write
    STATUS   current
    DESCRIPTION "Enabled(1) or Disabled (0)"
    ::= {psRelay2Masks 385}

r2TemperatureSensorError OBJECT-TYPE
    SYNTAX   INTEGER{disabled(0), enabled(1)}
    MAX-ACCESS  read-write
    STATUS   current
    DESCRIPTION "Enabled(1) or Disabled (0)"
    ::= {psRelay2Masks 386}

--DryContacts in psRelay2Masks
r2DryContact1 OBJECT-TYPE
    SYNTAX   INTEGER{disabled(0), enabled(1)}
    MAX-ACCESS  read-write
    STATUS   current
    DESCRIPTION "Enabled(1) or Disabled (0)"
    ::= {psRelay2Masks 416}

r2DryContact2 OBJECT-TYPE
    SYNTAX   INTEGER{disabled(0), enabled(1)}
    MAX-ACCESS  read-write
    STATUS   current
    DESCRIPTION "Enabled(1) or Disabled (0)"
    ::= {psRelay2Masks 417}

r2DryContact3 OBJECT-TYPE
    SYNTAX   INTEGER{disabled(0), enabled(1)}
    MAX-ACCESS  read-write
    STATUS   current
    DESCRIPTION "Enabled(1) or Disabled (0)"
    ::= {psRelay2Masks 418}

r2DryContact4 OBJECT-TYPE
    SYNTAX   INTEGER{disabled(0), enabled(1)}
    MAX-ACCESS  read-write
    STATUS   current
    DESCRIPTION "Enabled(1) or Disabled (0)"
    ::= {psRelay2Masks 419}

r2DryContact5 OBJECT-TYPE
    SYNTAX   INTEGER{disabled(0), enabled(1)}
    MAX-ACCESS  read-write
    STATUS   current
    DESCRIPTION "Enabled(1) or Disabled (0)"
    ::= {psRelay2Masks 420}

r2DryContact6 OBJECT-TYPE
    SYNTAX   INTEGER{disabled(0), enabled(1)}
    MAX-ACCESS  read-write
    STATUS   current
    DESCRIPTION "Enabled(1) or Disabled (0)"
    ::= {psRelay2Masks 421}

r2DryContact7 OBJECT-TYPE
    SYNTAX   INTEGER{disabled(0), enabled(1)}
    MAX-ACCESS  read-write
    STATUS   current
    DESCRIPTION "Enabled(1) or Disabled (0)"
    ::= {psRelay2Masks 422}

r2DryContact8 OBJECT-TYPE
    SYNTAX   INTEGER{disabled(0), enabled(1)}
    MAX-ACCESS  read-write
    STATUS   current
    DESCRIPTION "Enabled(1) or Disabled (0)"
    ::= {psRelay2Masks 423}

r2DryContact9 OBJECT-TYPE
    SYNTAX   INTEGER{disabled(0), enabled(1)}
    MAX-ACCESS  read-write
    STATUS   current
    DESCRIPTION "Enabled(1) or Disabled (0)"
    ::= {psRelay2Masks 424}

r2DryContact10 OBJECT-TYPE
    SYNTAX   INTEGER{disabled(0), enabled(1)}
    MAX-ACCESS  read-write
    STATUS   current
    DESCRIPTION "Enabled(1) or Disabled (0)"
    ::= {psRelay2Masks 425}

r2DryContact11 OBJECT-TYPE
    SYNTAX   INTEGER{disabled(0), enabled(1)}
    MAX-ACCESS  read-write
    STATUS   current
    DESCRIPTION "Enabled(1) or Disabled (0)"
    ::= {psRelay2Masks 426}

r2DryContact12 OBJECT-TYPE
    SYNTAX   INTEGER{disabled(0), enabled(1)}
    MAX-ACCESS  read-write
    STATUS   current
    DESCRIPTION "Enabled(1) or Disabled (0)"
    ::= {psRelay2Masks 427}

r2DryContact13 OBJECT-TYPE
    SYNTAX   INTEGER{disabled(0), enabled(1)}
    MAX-ACCESS  read-write
    STATUS   current
    DESCRIPTION "Enabled(1) or Disabled (0)"
    ::= {psRelay2Masks 428}

r2DryContact14 OBJECT-TYPE
    SYNTAX   INTEGER{disabled(0), enabled(1)}
    MAX-ACCESS  read-write
    STATUS   current
    DESCRIPTION "Enabled(1) or Disabled (0)"
    ::= {psRelay2Masks 429}

r2DryContact15 OBJECT-TYPE
    SYNTAX   INTEGER{disabled(0), enabled(1)}
    MAX-ACCESS  read-write
    STATUS   current
    DESCRIPTION "Enabled(1) or Disabled (0)"
    ::= {psRelay2Masks 430}

r2DryContact16 OBJECT-TYPE
    SYNTAX   INTEGER{disabled(0), enabled(1)}
    MAX-ACCESS  read-write
    STATUS   current
    DESCRIPTION "Enabled(1) or Disabled (0)"
    ::= {psRelay2Masks 431}

-- --------------------------------------

r2BatteryLiIonAlarm OBJECT-TYPE  
    SYNTAX   INTEGER{disabled(0), enabled(1)}
    MAX-ACCESS  read-write
    STATUS   current
    DESCRIPTION "Enabled(1) or Disabled (0)"
    ::= {psRelay2Masks 480}

--нет связи с BMS
r2BatteryBMSComFail OBJECT-TYPE  
    SYNTAX   INTEGER{disabled(0), enabled(1)}
    MAX-ACCESS  read-write
    STATUS   current
    DESCRIPTION "Enabled(1) or Disabled (0)"
    ::= {psRelay2Masks 481}

-- --------------------------------------

--InternalErrors in psRelay3Masks
r3InternallError OBJECT-TYPE
    SYNTAX   INTEGER{disabled(0), enabled(1)}
    MAX-ACCESS  read-write
    STATUS   current
    DESCRIPTION "Enabled(1) or Disabled (0)"
    ::= {psRelay3Masks 1}

--OutputAlarms in psRelay3Masks
r3LoadUnderVoltageAlarm OBJECT-TYPE
    SYNTAX   INTEGER{disabled(0), enabled(1)}
    MAX-ACCESS  read-write
    STATUS   current
    DESCRIPTION "Enabled(1) or Disabled (0)"
    ::= {psRelay3Masks 32}

r3LoadOverVoltageAlarm OBJECT-TYPE
    SYNTAX   INTEGER{disabled(0), enabled(1)}
    MAX-ACCESS  read-write
    STATUS   current
    DESCRIPTION "Enabled(1) or Disabled (0)"
    ::= {psRelay3Masks 33}

r3Termocompensation OBJECT-TYPE
    SYNTAX   INTEGER{disabled(0), enabled(1)}
    MAX-ACCESS  read-write
    STATUS   current
    DESCRIPTION "Enabled(1) or Disabled (0)"
    ::= {psRelay3Masks 34}

--LoadFuses in psRelay3Masks
r3LoadFuses1 OBJECT-TYPE
    SYNTAX   INTEGER{disabled(0), enabled(1)}
    MAX-ACCESS  read-write
    STATUS   current
    DESCRIPTION "Enabled(1) or Disabled (0)"
    ::= {psRelay3Masks 35}

r3LoadFuses2 OBJECT-TYPE
    SYNTAX   INTEGER{disabled(0), enabled(1)}
    MAX-ACCESS  read-write
    STATUS   current
    DESCRIPTION "Enabled(1) or Disabled (0)"
    ::= {psRelay3Masks 36}

r3LoadFuses3 OBJECT-TYPE
    SYNTAX   INTEGER{disabled(0), enabled(1)}
    MAX-ACCESS  read-write
    STATUS   current
    DESCRIPTION "Enabled(1) or Disabled (0)"
    ::= {psRelay3Masks 37}

r3LoadFuses4 OBJECT-TYPE
    SYNTAX   INTEGER{disabled(0), enabled(1)}
    MAX-ACCESS  read-write
    STATUS   current
    DESCRIPTION "Enabled(1) or Disabled (0)"
    ::= {psRelay3Masks 38}

r3LoadFuses5 OBJECT-TYPE
    SYNTAX   INTEGER{disabled(0), enabled(1)}
    MAX-ACCESS  read-write
    STATUS   current
    DESCRIPTION "Enabled(1) or Disabled (0)"
    ::= {psRelay3Masks 39}

r3LoadFuses6 OBJECT-TYPE
    SYNTAX   INTEGER{disabled(0), enabled(1)}
    MAX-ACCESS  read-write
    STATUS   current
    DESCRIPTION "Enabled(1) or Disabled (0)"
    ::= {psRelay3Masks 40}

r3LoadFuses7 OBJECT-TYPE
    SYNTAX   INTEGER{disabled(0), enabled(1)}
    MAX-ACCESS  read-write
    STATUS   current
    DESCRIPTION "Enabled(1) or Disabled (0)"
    ::= {psRelay3Masks 41}

r3LoadFuses8 OBJECT-TYPE
    SYNTAX   INTEGER{disabled(0), enabled(1)}
    MAX-ACCESS  read-write
    STATUS   current
    DESCRIPTION "Enabled(1) or Disabled (0)"
    ::= {psRelay3Masks 42}

r3LoadFuses9 OBJECT-TYPE
    SYNTAX   INTEGER{disabled(0), enabled(1)}
    MAX-ACCESS  read-write
    STATUS   current
    DESCRIPTION "Enabled(1) or Disabled (0)"
    ::= {psRelay3Masks 43}

r3LoadFuses10 OBJECT-TYPE
    SYNTAX   INTEGER{disabled(0), enabled(1)}
    MAX-ACCESS  read-write
    STATUS   current
    DESCRIPTION "Enabled(1) or Disabled (0)"
    ::= {psRelay3Masks 44}

r3LoadFuses11 OBJECT-TYPE
    SYNTAX   INTEGER{disabled(0), enabled(1)}
    MAX-ACCESS  read-write
    STATUS   current
    DESCRIPTION "Enabled(1) or Disabled (0)"
    ::= {psRelay3Masks 45}

r3LoadFuses12 OBJECT-TYPE
    SYNTAX   INTEGER{disabled(0), enabled(1)}
    MAX-ACCESS  read-write
    STATUS   current
    DESCRIPTION "Enabled(1) or Disabled (0)"
    ::= {psRelay3Masks 46}

r3LoadFuses13 OBJECT-TYPE
    SYNTAX   INTEGER{disabled(0), enabled(1)}
    MAX-ACCESS  read-write
    STATUS   current
    DESCRIPTION "Enabled(1) or Disabled (0)"
    ::= {psRelay3Masks 47}

r3LoadFuses14 OBJECT-TYPE
    SYNTAX   INTEGER{disabled(0), enabled(1)}
    MAX-ACCESS  read-write
    STATUS   current
    DESCRIPTION "Enabled(1) or Disabled (0)"
    ::= {psRelay3Masks 48}

r3LoadFuses15 OBJECT-TYPE
    SYNTAX   INTEGER{disabled(0), enabled(1)}
    MAX-ACCESS  read-write
    STATUS   current
    DESCRIPTION "Enabled(1) or Disabled (0)"
    ::= {psRelay3Masks 49}

r3LoadFuses16 OBJECT-TYPE
    SYNTAX   INTEGER{disabled(0), enabled(1)}
    MAX-ACCESS  read-write
    STATUS   current
    DESCRIPTION "Enabled(1) or Disabled (0)"
    ::= {psRelay3Masks 50}

r3LoadFuses17 OBJECT-TYPE
    SYNTAX   INTEGER{disabled(0), enabled(1)}
    MAX-ACCESS  read-write
    STATUS   current
    DESCRIPTION "Enabled(1) or Disabled (0)"
    ::= {psRelay3Masks 51}

r3LoadFuses18 OBJECT-TYPE
    SYNTAX   INTEGER{disabled(0), enabled(1)}
    MAX-ACCESS  read-write
    STATUS   current
    DESCRIPTION "Enabled(1) or Disabled (0)"
    ::= {psRelay3Masks 52}

r3LoadFuses19 OBJECT-TYPE
    SYNTAX   INTEGER{disabled(0), enabled(1)}
    MAX-ACCESS  read-write
    STATUS   current
    DESCRIPTION "Enabled(1) or Disabled (0)"
    ::= {psRelay3Masks 53}

r3LoadFuses20 OBJECT-TYPE
    SYNTAX   INTEGER{disabled(0), enabled(1)}
    MAX-ACCESS  read-write
    STATUS   current
    DESCRIPTION "Enabled(1) or Disabled (0)"
    ::= {psRelay3Masks 54}

r3LoadFuses21 OBJECT-TYPE
    SYNTAX   INTEGER{disabled(0), enabled(1)}
    MAX-ACCESS  read-write
    STATUS   current
    DESCRIPTION "Enabled(1) or Disabled (0)"
    ::= {psRelay3Masks 55}

r3LoadFuses22 OBJECT-TYPE
    SYNTAX   INTEGER{disabled(0), enabled(1)}
    MAX-ACCESS  read-write
    STATUS   current
    DESCRIPTION "Enabled(1) or Disabled (0)"
    ::= {psRelay3Masks 56}

r3LoadFuses23 OBJECT-TYPE
    SYNTAX   INTEGER{disabled(0), enabled(1)}
    MAX-ACCESS  read-write
    STATUS   current
    DESCRIPTION "Enabled(1) or Disabled (0)"
    ::= {psRelay3Masks 57}

r3LoadFuses24 OBJECT-TYPE
    SYNTAX   INTEGER{disabled(0), enabled(1)}
    MAX-ACCESS  read-write
    STATUS   current
    DESCRIPTION "Enabled(1) or Disabled (0)"
    ::= {psRelay3Masks 58}

r3LoadFuses25 OBJECT-TYPE
    SYNTAX   INTEGER{disabled(0), enabled(1)}
    MAX-ACCESS  read-write
    STATUS   current
    DESCRIPTION "Enabled(1) or Disabled (0)"
    ::= {psRelay3Masks 59}

r3LoadFuses26 OBJECT-TYPE
    SYNTAX   INTEGER{disabled(0), enabled(1)}
    MAX-ACCESS  read-write
    STATUS   current
    DESCRIPTION "Enabled(1) or Disabled (0)"
    ::= {psRelay3Masks 60}

r3LoadFuses27 OBJECT-TYPE
    SYNTAX   INTEGER{disabled(0), enabled(1)}
    MAX-ACCESS  read-write
    STATUS   current
    DESCRIPTION "Enabled(1) or Disabled (0)"
    ::= {psRelay3Masks 61}

r3LoadFuses28 OBJECT-TYPE
    SYNTAX   INTEGER{disabled(0), enabled(1)}
    MAX-ACCESS  read-write
    STATUS   current
    DESCRIPTION "Enabled(1) or Disabled (0)"
    ::= {psRelay3Masks 62}

r3LoadFuses29 OBJECT-TYPE
    SYNTAX   INTEGER{disabled(0), enabled(1)}
    MAX-ACCESS  read-write
    STATUS   current
    DESCRIPTION "Enabled(1) or Disabled (0)"
    ::= {psRelay3Masks 63}

r3LoadFuses30 OBJECT-TYPE
    SYNTAX   INTEGER{disabled(0), enabled(1)}
    MAX-ACCESS  read-write
    STATUS   current
    DESCRIPTION "Enabled(1) or Disabled (0)"
    ::= {psRelay3Masks 64}

r3LoadFuses31 OBJECT-TYPE
    SYNTAX   INTEGER{disabled(0), enabled(1)}
    MAX-ACCESS  read-write
    STATUS   current
    DESCRIPTION "Enabled(1) or Disabled (0)"
    ::= {psRelay3Masks 65}

r3LoadFuses32 OBJECT-TYPE
    SYNTAX   INTEGER{disabled(0), enabled(1)}
    MAX-ACCESS  read-write
    STATUS   current
    DESCRIPTION "Enabled(1) or Disabled (0)"
    ::= {psRelay3Masks 66}

r3LoadFuses33 OBJECT-TYPE
    SYNTAX   INTEGER{disabled(0), enabled(1)}
    MAX-ACCESS  read-write
    STATUS   current
    DESCRIPTION "Enabled(1) or Disabled (0)"
    ::= {psRelay3Masks 67}

r3LoadFuses34 OBJECT-TYPE
    SYNTAX   INTEGER{disabled(0), enabled(1)}
    MAX-ACCESS  read-write
    STATUS   current
    DESCRIPTION "Enabled(1) or Disabled (0)"
    ::= {psRelay3Masks 68}

r3LoadFuses35 OBJECT-TYPE
    SYNTAX   INTEGER{disabled(0), enabled(1)}
    MAX-ACCESS  read-write
    STATUS   current
    DESCRIPTION "Enabled(1) or Disabled (0)"
    ::= {psRelay3Masks 69}

r3LoadFuses36 OBJECT-TYPE
    SYNTAX   INTEGER{disabled(0), enabled(1)}
    MAX-ACCESS  read-write
    STATUS   current
    DESCRIPTION "Enabled(1) or Disabled (0)"
    ::= {psRelay3Masks 70}

r3LoadFuses37 OBJECT-TYPE
    SYNTAX   INTEGER{disabled(0), enabled(1)}
    MAX-ACCESS  read-write
    STATUS   current
    DESCRIPTION "Enabled(1) or Disabled (0)"
    ::= {psRelay3Masks 71}

r3LoadFuses38 OBJECT-TYPE
    SYNTAX   INTEGER{disabled(0), enabled(1)}
    MAX-ACCESS  read-write
    STATUS   current
    DESCRIPTION "Enabled(1) or Disabled (0)"
    ::= {psRelay3Masks 72}

r3LoadFuses39 OBJECT-TYPE
    SYNTAX   INTEGER{disabled(0), enabled(1)}
    MAX-ACCESS  read-write
    STATUS   current
    DESCRIPTION "Enabled(1) or Disabled (0)"
    ::= {psRelay3Masks 73}

r3LoadFuses40 OBJECT-TYPE
    SYNTAX   INTEGER{disabled(0), enabled(1)}
    MAX-ACCESS  read-write
    STATUS   current
    DESCRIPTION "Enabled(1) or Disabled (0)"
    ::= {psRelay3Masks 74}

r3LoadFuses41 OBJECT-TYPE
    SYNTAX   INTEGER{disabled(0), enabled(1)}
    MAX-ACCESS  read-write
    STATUS   current
    DESCRIPTION "Enabled(1) or Disabled (0)"
    ::= {psRelay3Masks 75}

r3LoadFuses42 OBJECT-TYPE
    SYNTAX   INTEGER{disabled(0), enabled(1)}
    MAX-ACCESS  read-write
    STATUS   current
    DESCRIPTION "Enabled(1) or Disabled (0)"
    ::= {psRelay3Masks 76}

r3LoadFuses43 OBJECT-TYPE
    SYNTAX   INTEGER{disabled(0), enabled(1)}
    MAX-ACCESS  read-write
    STATUS   current
    DESCRIPTION "Enabled(1) or Disabled (0)"
    ::= {psRelay3Masks 77}

r3LoadFuses44 OBJECT-TYPE
    SYNTAX   INTEGER{disabled(0), enabled(1)}
    MAX-ACCESS  read-write
    STATUS   current
    DESCRIPTION "Enabled(1) or Disabled (0)"
    ::= {psRelay3Masks 78}

r3LoadFuses45 OBJECT-TYPE
    SYNTAX   INTEGER{disabled(0), enabled(1)}
    MAX-ACCESS  read-write
    STATUS   current
    DESCRIPTION "Enabled(1) or Disabled (0)"
    ::= {psRelay3Masks 79}

r3LoadFuses46 OBJECT-TYPE
    SYNTAX   INTEGER{disabled(0), enabled(1)}
    MAX-ACCESS  read-write
    STATUS   current
    DESCRIPTION "Enabled(1) or Disabled (0)"
    ::= {psRelay3Masks 80}

r3LoadFuses47 OBJECT-TYPE
    SYNTAX   INTEGER{disabled(0), enabled(1)}
    MAX-ACCESS  read-write
    STATUS   current
    DESCRIPTION "Enabled(1) or Disabled (0)"
    ::= {psRelay3Masks 81}

r3LoadFuses48 OBJECT-TYPE
    SYNTAX   INTEGER{disabled(0), enabled(1)}
    MAX-ACCESS  read-write
    STATUS   current
    DESCRIPTION "Enabled(1) or Disabled (0)"
    ::= {psRelay3Masks 82}

r3LoadFuses49 OBJECT-TYPE
    SYNTAX   INTEGER{disabled(0), enabled(1)}
    MAX-ACCESS  read-write
    STATUS   current
    DESCRIPTION "Enabled(1) or Disabled (0)"
    ::= {psRelay3Masks 83}

r3LoadFuses50 OBJECT-TYPE
    SYNTAX   INTEGER{disabled(0), enabled(1)}
    MAX-ACCESS  read-write
    STATUS   current
    DESCRIPTION "Enabled(1) or Disabled (0)"
    ::= {psRelay3Masks 84}

r3LoadFuses51 OBJECT-TYPE
    SYNTAX   INTEGER{disabled(0), enabled(1)}
    MAX-ACCESS  read-write
    STATUS   current
    DESCRIPTION "Enabled(1) or Disabled (0)"
    ::= {psRelay3Masks 85}

r3LoadFuses52 OBJECT-TYPE
    SYNTAX   INTEGER{disabled(0), enabled(1)}
    MAX-ACCESS  read-write
    STATUS   current
    DESCRIPTION "Enabled(1) or Disabled (0)"
    ::= {psRelay3Masks 86}

r3UKDVAlarm OBJECT-TYPE
    SYNTAX   INTEGER{disabled(0), enabled(1)}
    MAX-ACCESS  read-write
    STATUS   current
    DESCRIPTION "Enabled(1) or Disabled (0)"
    ::= {psRelay3Masks 87}

--Battery Events in psRelay3Masks
r3BatteryDischarge OBJECT-TYPE
    SYNTAX   INTEGER{disabled(0), enabled(1)}
    MAX-ACCESS  read-write
    STATUS   current
    DESCRIPTION "Enabled(1) or Disabled (0)"
    ::= {psRelay3Masks 96}

r3LowBatteryVoltage OBJECT-TYPE
    SYNTAX   INTEGER{disabled(0), enabled(1)}
    MAX-ACCESS  read-write
    STATUS   current
    DESCRIPTION "Enabled(1) or Disabled (0)"
    ::= {psRelay3Masks 97}

r3BatteryCharge OBJECT-TYPE
    SYNTAX   INTEGER{disabled(0), enabled(1)}
    MAX-ACCESS  read-write
    STATUS   current
    DESCRIPTION "Enabled(1) or Disabled (0)"
    ::= {psRelay3Masks 98}

r3BatteryBoost OBJECT-TYPE
    SYNTAX   INTEGER{disabled(0), enabled(1)}
    MAX-ACCESS  read-write
    STATUS   current
    DESCRIPTION "Enabled(1) or Disabled (0)"
    ::= {psRelay3Masks 99}

r3BatteryFloat OBJECT-TYPE
    SYNTAX   INTEGER{disabled(0), enabled(1)}
    MAX-ACCESS  read-write
    STATUS   current
    DESCRIPTION "Enabled(1) or Disabled (0)"
    ::= {psRelay3Masks 100}

r3BatteryEqualize OBJECT-TYPE
    SYNTAX   INTEGER{disabled(0), enabled(1)}
    MAX-ACCESS  read-write
    STATUS   current
    DESCRIPTION "Enabled(1) or Disabled (0)"
    ::= {psRelay3Masks 101}

r3BatteryTest OBJECT-TYPE
    SYNTAX   INTEGER{disabled(0), enabled(1)}
    MAX-ACCESS  read-write
    STATUS   current
    DESCRIPTION "Enabled(1) or Disabled (0)"
    ::= {psRelay3Masks 102}

r3BatteryFuse1Off OBJECT-TYPE
    SYNTAX   INTEGER{disabled(0), enabled(1)}
    MAX-ACCESS  read-write
    STATUS   current
    DESCRIPTION "Enabled(1) or Disabled (0)"
    ::= {psRelay3Masks 103}

r3BatteryFuse2Off OBJECT-TYPE
    SYNTAX   INTEGER{disabled(0), enabled(1)}
    MAX-ACCESS  read-write
    STATUS   current
    DESCRIPTION "Enabled(1) or Disabled (0)"
    ::= {psRelay3Masks 104}

r3BatteryFuse3Off OBJECT-TYPE
    SYNTAX   INTEGER{disabled(0), enabled(1)}
    MAX-ACCESS  read-write
    STATUS   current
    DESCRIPTION "Enabled(1) or Disabled (0)"
    ::= {psRelay3Masks 105}

r3BatteryFuse4Off OBJECT-TYPE
    SYNTAX   INTEGER{disabled(0), enabled(1)}
    MAX-ACCESS  read-write
    STATUS   current
    DESCRIPTION "Enabled(1) or Disabled (0)"
    ::= {psRelay3Masks 106}

---------------------------------------------------

r3BatteryBlockElGr1Alarm OBJECT-TYPE
    SYNTAX   INTEGER{disabled(0), enabled(1)}
    MAX-ACCESS  read-write
    STATUS   current
    DESCRIPTION "Enabled(1) or Disabled (0)"
    ::= {psRelay3Masks 111}

r3BatteryBlockElGr2Alarm OBJECT-TYPE
    SYNTAX   INTEGER{disabled(0), enabled(1)}
    MAX-ACCESS  read-write
    STATUS   current
    DESCRIPTION "Enabled(1) or Disabled (0)"
    ::= {psRelay3Masks 112}

r3BatteryBlockElGr3Alarm OBJECT-TYPE
    SYNTAX   INTEGER{disabled(0), enabled(1)}
    MAX-ACCESS  read-write
    STATUS   current
    DESCRIPTION "Enabled(1) or Disabled (0)"
    ::= {psRelay3Masks 113}

r3BatteryBlockElGr4Alarm OBJECT-TYPE
    SYNTAX   INTEGER{disabled(0), enabled(1)}
    MAX-ACCESS  read-write
    STATUS   current
    DESCRIPTION "Enabled(1) or Disabled (0)"
    ::= {psRelay3Masks 114}
----------------------------------------------------

r3UPKBAlarm OBJECT-TYPE
    SYNTAX   INTEGER{disabled(0), enabled(1)}
    MAX-ACCESS  read-write
    STATUS   current
    DESCRIPTION "Enabled(1) or Disabled (0)"
    ::= {psRelay3Masks 119}

r3ChargeCurrentLess1A OBJECT-TYPE
    SYNTAX   INTEGER{disabled(0), enabled(1)}
    MAX-ACCESS  read-write
    STATUS   current
    DESCRIPTION "Enabled(1) or Disabled (0)"
    ::= {psRelay3Masks 120}

r3ChargeCurrentLess2A OBJECT-TYPE
    SYNTAX   INTEGER{disabled(0), enabled(1)}
    MAX-ACCESS  read-write
    STATUS   current
    DESCRIPTION "Enabled(1) or Disabled (0)"
    ::= {psRelay3Masks 121}

r3ChargeCurrentLess3A OBJECT-TYPE
    SYNTAX   INTEGER{disabled(0), enabled(1)}
    MAX-ACCESS  read-write
    STATUS   current
    DESCRIPTION "Enabled(1) or Disabled (0)"
    ::= {psRelay3Masks 122}

r3ChargeCurrentLess4A OBJECT-TYPE
    SYNTAX   INTEGER{disabled(0), enabled(1)}
    MAX-ACCESS  read-write
    STATUS   current
    DESCRIPTION "Enabled(1) or Disabled (0)"
    ::= {psRelay3Masks 123}

r3ChargeCurrentLess5A OBJECT-TYPE
    SYNTAX   INTEGER{disabled(0), enabled(1)}
    MAX-ACCESS  read-write
    STATUS   current
    DESCRIPTION "Enabled(1) or Disabled (0)"
    ::= {psRelay3Masks 124}

r3BatteryOverheat OBJECT-TYPE
    SYNTAX   INTEGER{disabled(0), enabled(1)}
    MAX-ACCESS  read-write
    STATUS   current
    DESCRIPTION "Enabled(1) or Disabled (0)"
    ::= {psRelay3Masks 125}

-------------------------------------------------------------------------------------------
-------------------------------------------------------------------------------------------
r3BatteryShortTest OBJECT-TYPE
    SYNTAX   INTEGER{disabled(0), enabled(1)}
    MAX-ACCESS  read-write
    STATUS   current
    DESCRIPTION "Enabled(1) or Disabled (0)"
    ::= {psRelay3Masks 126}

r3BatteryShortTestFail OBJECT-TYPE  
    SYNTAX   INTEGER{disabled(0), enabled(1)}
    MAX-ACCESS  read-write
    STATUS   current
    DESCRIPTION "Enabled(1) or Disabled (0)"
    ::= {psRelay3Masks 127}

-------------------------------------------------------------------------------------------
-------------------------------------------------------------------------------------------

r3BLVDoff OBJECT-TYPE
    SYNTAX   INTEGER{disabled(0), enabled(1)}
    MAX-ACCESS  read-write
    STATUS   current
    DESCRIPTION "Enabled(1) or Disabled (0)"
    ::= {psRelay3Masks 128}

r3LLVD1off OBJECT-TYPE
    SYNTAX   INTEGER{disabled(0), enabled(1)}
    MAX-ACCESS  read-write
    STATUS   current
    DESCRIPTION "Enabled(1) or Disabled (0)"
    ::= {psRelay3Masks 129}

r3LLVD2off OBJECT-TYPE
    SYNTAX   INTEGER{disabled(0), enabled(1)}
    MAX-ACCESS  read-write
    STATUS   current
    DESCRIPTION "Enabled(1) or Disabled (0)"
    ::= {psRelay3Masks 130}

--VBVAlarm in psRelay3Masks
r3VBV1Alarm OBJECT-TYPE
    SYNTAX   INTEGER{disabled(0), enabled(1)}
    MAX-ACCESS  read-write
    STATUS   current
    DESCRIPTION "Alarm of rectifier1 Enabled(1) or Disabled (0)"
    ::= {psRelay3Masks 160}

r3VBV2Alarm OBJECT-TYPE
    SYNTAX   INTEGER{disabled(0), enabled(1)}
    MAX-ACCESS  read-write
    STATUS   current
    DESCRIPTION "Alarm of rectifier2 Enabled(1) or Disabled (0)"
    ::= {psRelay3Masks 161}

r3VBV3Alarm OBJECT-TYPE
    SYNTAX   INTEGER{disabled(0), enabled(1)}
    MAX-ACCESS  read-write
    STATUS   current
    DESCRIPTION "Alarm of rectifier3 Enabled(1) or Disabled (0)"
    ::= {psRelay3Masks 162}

r3VBV4Alarm OBJECT-TYPE
    SYNTAX   INTEGER{disabled(0), enabled(1)}
    MAX-ACCESS  read-write
    STATUS   current
    DESCRIPTION "Alarm of rectifier4 Enabled(1) or Disabled (0)"
    ::= {psRelay3Masks 163}

r3VBV5Alarm OBJECT-TYPE
    SYNTAX   INTEGER{disabled(0), enabled(1)}
    MAX-ACCESS  read-write
    STATUS   current
    DESCRIPTION "Alarm of rectifier5 Enabled(1) or Disabled (0)"
    ::= {psRelay3Masks 164}

r3VBV6Alarm OBJECT-TYPE
    SYNTAX   INTEGER{disabled(0), enabled(1)}
    MAX-ACCESS  read-write
    STATUS   current
    DESCRIPTION "Alarm of rectifier6 Enabled(1) or Disabled (0)"
    ::= {psRelay3Masks 165}

r3VBV7Alarm OBJECT-TYPE
    SYNTAX   INTEGER{disabled(0), enabled(1)}
    MAX-ACCESS  read-write
    STATUS   current
    DESCRIPTION "Alarm of rectifier7 Enabled(1) or Disabled (0)"
    ::= {psRelay3Masks 166}

r3VBV8Alarm OBJECT-TYPE
    SYNTAX   INTEGER{disabled(0), enabled(1)}
    MAX-ACCESS  read-write
    STATUS   current
    DESCRIPTION "Alarm of rectifier8 Enabled(1) or Disabled (0)"
    ::= {psRelay3Masks 167}

r3VBV9Alarm OBJECT-TYPE
    SYNTAX   INTEGER{disabled(0), enabled(1)}
    MAX-ACCESS  read-write
    STATUS   current
    DESCRIPTION "Alarm of rectifier9 Enabled(1) or Disabled (0)"
    ::= {psRelay3Masks 168}

r3VBV10Alarm OBJECT-TYPE
    SYNTAX   INTEGER{disabled(0), enabled(1)}
    MAX-ACCESS  read-write
    STATUS   current
    DESCRIPTION "Alarm of rectifier10 Enabled(1) or Disabled (0)"
    ::= {psRelay3Masks 169}

r3VBV11Alarm OBJECT-TYPE
    SYNTAX   INTEGER{disabled(0), enabled(1)}
    MAX-ACCESS  read-write
    STATUS   current
    DESCRIPTION "Alarm of rectifier11 Enabled(1) or Disabled (0)"
    ::= {psRelay3Masks 170}

r3VBV12Alarm OBJECT-TYPE
    SYNTAX   INTEGER{disabled(0), enabled(1)}
    MAX-ACCESS  read-write
    STATUS   current
    DESCRIPTION "Alarm of rectifier12 Enabled(1) or Disabled (0)"
    ::= {psRelay3Masks 171}

r3VBV13Alarm OBJECT-TYPE
    SYNTAX   INTEGER{disabled(0), enabled(1)}
    MAX-ACCESS  read-write
    STATUS   current
    DESCRIPTION "Alarm of rectifier13 Enabled(1) or Disabled (0)"
    ::= {psRelay3Masks 172}

r3VBV14Alarm OBJECT-TYPE
    SYNTAX   INTEGER{disabled(0), enabled(1)}
    MAX-ACCESS  read-write
    STATUS   current
    DESCRIPTION "Alarm of rectifier14 Enabled(1) or Disabled (0)"
    ::= {psRelay3Masks 173}

r3VBV15Alarm OBJECT-TYPE
    SYNTAX   INTEGER{disabled(0), enabled(1)}
    MAX-ACCESS  read-write
    STATUS   current
    DESCRIPTION "Alarm of rectifier15 Enabled(1) or Disabled (0)"
    ::= {psRelay3Masks 174}

r3VBV16Alarm OBJECT-TYPE
    SYNTAX   INTEGER{disabled(0), enabled(1)}
    MAX-ACCESS  read-write
    STATUS   current
    DESCRIPTION "Alarm of rectifier16 Enabled(1) or Disabled (0)"
    ::= {psRelay3Masks 175}

r3VBV17Alarm OBJECT-TYPE
    SYNTAX   INTEGER{disabled(0), enabled(1)}
    MAX-ACCESS  read-write
    STATUS   current
    DESCRIPTION "Alarm of rectifier17 Enabled(1) or Disabled (0)"
    ::= {psRelay3Masks 176}

r3VBV18Alarm OBJECT-TYPE
    SYNTAX   INTEGER{disabled(0), enabled(1)}
    MAX-ACCESS  read-write
    STATUS   current
    DESCRIPTION "Alarm of rectifier18 Enabled(1) or Disabled (0)"
    ::= {psRelay3Masks 177}

r3VBV19Alarm OBJECT-TYPE
    SYNTAX   INTEGER{disabled(0), enabled(1)}
    MAX-ACCESS  read-write
    STATUS   current
    DESCRIPTION "Alarm of rectifier19 Enabled(1) or Disabled (0)"
    ::= {psRelay3Masks 178}

r3VBV20Alarm OBJECT-TYPE
    SYNTAX   INTEGER{disabled(0), enabled(1)}
    MAX-ACCESS  read-write
    STATUS   current
    DESCRIPTION "Alarm of rectifier20 Enabled(1) or Disabled (0)"
    ::= {psRelay3Masks 179}

r3VBV21Alarm OBJECT-TYPE
    SYNTAX   INTEGER{disabled(0), enabled(1)}
    MAX-ACCESS  read-write
    STATUS   current
    DESCRIPTION "Alarm of rectifier21 Enabled(1) or Disabled (0)"
    ::= {psRelay3Masks 180}

r3VBV22Alarm OBJECT-TYPE
    SYNTAX   INTEGER{disabled(0), enabled(1)}
    MAX-ACCESS  read-write
    STATUS   current
    DESCRIPTION "Alarm of rectifier22 Enabled(1) or Disabled (0)"
    ::= {psRelay3Masks 181}

r3VBV23Alarm OBJECT-TYPE
    SYNTAX   INTEGER{disabled(0), enabled(1)}
    MAX-ACCESS  read-write
    STATUS   current
    DESCRIPTION "Alarm of rectifier23 Enabled(1) or Disabled (0)"
    ::= {psRelay3Masks 182}

r3VBV24Alarm OBJECT-TYPE
    SYNTAX   INTEGER{disabled(0), enabled(1)}
    MAX-ACCESS  read-write
    STATUS   current
    DESCRIPTION "Alarm of rectifier24 Enabled(1) or Disabled (0)"
    ::= {psRelay3Masks 183}

r3VBV25Alarm OBJECT-TYPE
    SYNTAX   INTEGER{disabled(0), enabled(1)}
    MAX-ACCESS  read-write
    STATUS   current
    DESCRIPTION "Alarm of rectifier25 Enabled(1) or Disabled (0)"
    ::= {psRelay3Masks 184}

r3VBV26Alarm OBJECT-TYPE
    SYNTAX   INTEGER{disabled(0), enabled(1)}
    MAX-ACCESS  read-write
    STATUS   current
    DESCRIPTION "Alarm of rectifier26 Enabled(1) or Disabled (0)"
    ::= {psRelay3Masks 185}

r3VBV27Alarm OBJECT-TYPE
    SYNTAX   INTEGER{disabled(0), enabled(1)}
    MAX-ACCESS  read-write
    STATUS   current
    DESCRIPTION "Alarm of rectifier27 Enabled(1) or Disabled (0)"
    ::= {psRelay3Masks 186}

r3VBV28Alarm OBJECT-TYPE
    SYNTAX   INTEGER{disabled(0), enabled(1)}
    MAX-ACCESS  read-write
    STATUS   current
    DESCRIPTION "Alarm of rectifier28 Enabled(1) or Disabled (0)"
    ::= {psRelay3Masks 187}

r3VBV29Alarm OBJECT-TYPE
    SYNTAX   INTEGER{disabled(0), enabled(1)}
    MAX-ACCESS  read-write
    STATUS   current
    DESCRIPTION "Alarm of rectifier29 Enabled(1) or Disabled (0)"
    ::= {psRelay3Masks 188}

r3VBV30Alarm OBJECT-TYPE
    SYNTAX   INTEGER{disabled(0), enabled(1)}
    MAX-ACCESS  read-write
    STATUS   current
    DESCRIPTION "Alarm of rectifier30 Enabled(1) or Disabled (0)"
    ::= {psRelay3Masks 189}

r3VBV31Alarm OBJECT-TYPE
    SYNTAX   INTEGER{disabled(0), enabled(1)}
    MAX-ACCESS  read-write
    STATUS   current
    DESCRIPTION "Alarm of rectifier31 Enabled(1) or Disabled (0)"
    ::= {psRelay3Masks 190}

r3VBV32Alarm OBJECT-TYPE
    SYNTAX   INTEGER{disabled(0), enabled(1)}
    MAX-ACCESS  read-write
    STATUS   current
    DESCRIPTION "Alarm of rectifier32 Enabled(1) or Disabled (0)"
    ::= {psRelay3Masks 191}

r3VBV33Alarm OBJECT-TYPE
    SYNTAX   INTEGER{disabled(0), enabled(1)}
    MAX-ACCESS  read-write
    STATUS   current
    DESCRIPTION "Alarm of rectifier33 Enabled(1) or Disabled (0)"
    ::= {psRelay3Masks 192}

r3VBV34Alarm OBJECT-TYPE
    SYNTAX   INTEGER{disabled(0), enabled(1)}
    MAX-ACCESS  read-write
    STATUS   current
    DESCRIPTION "Alarm of rectifier34 Enabled(1) or Disabled (0)"
    ::= {psRelay3Masks 193}

r3VBV35Alarm OBJECT-TYPE
    SYNTAX   INTEGER{disabled(0), enabled(1)}
    MAX-ACCESS  read-write
    STATUS   current
    DESCRIPTION "Alarm of rectifier35 Enabled(1) or Disabled (0)"
    ::= {psRelay3Masks 194}

r3VBV36Alarm OBJECT-TYPE
    SYNTAX   INTEGER{disabled(0), enabled(1)}
    MAX-ACCESS  read-write
    STATUS   current
    DESCRIPTION "Alarm of rectifier36 Enabled(1) or Disabled (0)"
    ::= {psRelay3Masks 195}

r3VBV37Alarm OBJECT-TYPE
    SYNTAX   INTEGER{disabled(0), enabled(1)}
    MAX-ACCESS  read-write
    STATUS   current
    DESCRIPTION "Alarm of rectifier37 Enabled(1) or Disabled (0)"
    ::= {psRelay3Masks 196}

r3VBV38Alarm OBJECT-TYPE
    SYNTAX   INTEGER{disabled(0), enabled(1)}
    MAX-ACCESS  read-write
    STATUS   current
    DESCRIPTION "Alarm of rectifier38 Enabled(1) or Disabled (0)"
    ::= {psRelay3Masks 197}

r3VBV39Alarm OBJECT-TYPE
    SYNTAX   INTEGER{disabled(0), enabled(1)}
    MAX-ACCESS  read-write
    STATUS   current
    DESCRIPTION "Alarm of rectifier39 Enabled(1) or Disabled (0)"
    ::= {psRelay3Masks 198}

r3VBV40Alarm OBJECT-TYPE
    SYNTAX   INTEGER{disabled(0), enabled(1)}
    MAX-ACCESS  read-write
    STATUS   current
    DESCRIPTION "Alarm of rectifier40 Enabled(1) or Disabled (0)"
    ::= {psRelay3Masks 199}

r3VBV41Alarm OBJECT-TYPE
    SYNTAX   INTEGER{disabled(0), enabled(1)}
    MAX-ACCESS  read-write
    STATUS   current
    DESCRIPTION "Alarm of rectifier41 Enabled(1) or Disabled (0)"
    ::= {psRelay3Masks 200}

r3VBV42Alarm OBJECT-TYPE
    SYNTAX   INTEGER{disabled(0), enabled(1)}
    MAX-ACCESS  read-write
    STATUS   current
    DESCRIPTION "Alarm of rectifier42 Enabled(1) or Disabled (0)"
    ::= {psRelay3Masks 201}

r3VBV43Alarm OBJECT-TYPE
    SYNTAX   INTEGER{disabled(0), enabled(1)}
    MAX-ACCESS  read-write
    STATUS   current
    DESCRIPTION "Alarm of rectifier43 Enabled(1) or Disabled (0)"
    ::= {psRelay3Masks 202}

r3VBV44Alarm OBJECT-TYPE
    SYNTAX   INTEGER{disabled(0), enabled(1)}
    MAX-ACCESS  read-write
    STATUS   current
    DESCRIPTION "Alarm of rectifier44 Enabled(1) or Disabled (0)"
    ::= {psRelay3Masks 203}

r3VBV45Alarm OBJECT-TYPE
    SYNTAX   INTEGER{disabled(0), enabled(1)}
    MAX-ACCESS  read-write
    STATUS   current
    DESCRIPTION "Alarm of rectifier45 Enabled(1) or Disabled (0)"
    ::= {psRelay3Masks 204}

r3VBV46Alarm OBJECT-TYPE
    SYNTAX   INTEGER{disabled(0), enabled(1)}
    MAX-ACCESS  read-write
    STATUS   current
    DESCRIPTION "Alarm of rectifier46 Enabled(1) or Disabled (0)"
    ::= {psRelay3Masks 205}

r3VBV47Alarm OBJECT-TYPE
    SYNTAX   INTEGER{disabled(0), enabled(1)}
    MAX-ACCESS  read-write
    STATUS   current
    DESCRIPTION "Alarm of rectifier47 Enabled(1) or Disabled (0)"
    ::= {psRelay3Masks 206}

r3VBV48Alarm OBJECT-TYPE
    SYNTAX   INTEGER{disabled(0), enabled(1)}
    MAX-ACCESS  read-write
    STATUS   current
    DESCRIPTION "Alarm of rectifier48 Enabled(1) or Disabled (0)"
    ::= {psRelay3Masks 207}

r3VBV49Alarm OBJECT-TYPE
    SYNTAX   INTEGER{disabled(0), enabled(1)}
    MAX-ACCESS  read-write
    STATUS   current
    DESCRIPTION "Alarm of rectifier49 Enabled(1) or Disabled (0)"
    ::= {psRelay3Masks 208}

r3VBV50Alarm OBJECT-TYPE
    SYNTAX   INTEGER{disabled(0), enabled(1)}
    MAX-ACCESS  read-write
    STATUS   current
    DESCRIPTION "Alarm of rectifier50 Enabled(1) or Disabled (0)"
    ::= {psRelay3Masks 209}

r3VBV51Alarm OBJECT-TYPE
    SYNTAX   INTEGER{disabled(0), enabled(1)}
    MAX-ACCESS  read-write
    STATUS   current
    DESCRIPTION "Alarm of rectifier51 Enabled(1) or Disabled (0)"
    ::= {psRelay3Masks 210}

r3VBV52Alarm OBJECT-TYPE
    SYNTAX   INTEGER{disabled(0), enabled(1)}
    MAX-ACCESS  read-write
    STATUS   current
    DESCRIPTION "Alarm of rectifier52 Enabled(1) or Disabled (0)"
    ::= {psRelay3Masks 211}

r3VBV53Alarm OBJECT-TYPE
    SYNTAX   INTEGER{disabled(0), enabled(1)}
    MAX-ACCESS  read-write
    STATUS   current
    DESCRIPTION "Alarm of rectifier53 Enabled(1) or Disabled (0)"
    ::= {psRelay3Masks 212}

r3VBV54Alarm OBJECT-TYPE
    SYNTAX   INTEGER{disabled(0), enabled(1)}
    MAX-ACCESS  read-write
    STATUS   current
    DESCRIPTION "Alarm of rectifier54 Enabled(1) or Disabled (0)"
    ::= {psRelay3Masks 213}

r3VBV55Alarm OBJECT-TYPE
    SYNTAX   INTEGER{disabled(0), enabled(1)}
    MAX-ACCESS  read-write
    STATUS   current
    DESCRIPTION "Alarm of rectifier55 Enabled(1) or Disabled (0)"
    ::= {psRelay3Masks 214}

r3VBV56Alarm OBJECT-TYPE
    SYNTAX   INTEGER{disabled(0), enabled(1)}
    MAX-ACCESS  read-write
    STATUS   current
    DESCRIPTION "Alarm of rectifier56 Enabled(1) or Disabled (0)"
    ::= {psRelay3Masks 215}

r3VBV57Alarm OBJECT-TYPE
    SYNTAX   INTEGER{disabled(0), enabled(1)}
    MAX-ACCESS  read-write
    STATUS   current
    DESCRIPTION "Alarm of rectifier57 Enabled(1) or Disabled (0)"
    ::= {psRelay3Masks 216}

r3VBV58Alarm OBJECT-TYPE
    SYNTAX   INTEGER{disabled(0), enabled(1)}
    MAX-ACCESS  read-write
    STATUS   current
    DESCRIPTION "Alarm of rectifier58 Enabled(1) or Disabled (0)"
    ::= {psRelay3Masks 217}

r3VBV59Alarm OBJECT-TYPE
    SYNTAX   INTEGER{disabled(0), enabled(1)}
    MAX-ACCESS  read-write
    STATUS   current
    DESCRIPTION "Alarm of rectifier59 Enabled(1) or Disabled (0)"
    ::= {psRelay3Masks 218}

r3VBV60Alarm OBJECT-TYPE
    SYNTAX   INTEGER{disabled(0), enabled(1)}
    MAX-ACCESS  read-write
    STATUS   current
    DESCRIPTION "Alarm of rectifier60 Enabled(1) or Disabled (0)"
    ::= {psRelay3Masks 219}

r3VBV61Alarm OBJECT-TYPE
    SYNTAX   INTEGER{disabled(0), enabled(1)}
    MAX-ACCESS  read-write
    STATUS   current
    DESCRIPTION "Alarm of rectifier61 Enabled(1) or Disabled (0)"
    ::= {psRelay3Masks 220}

r3VBV62Alarm OBJECT-TYPE
    SYNTAX   INTEGER{disabled(0), enabled(1)}
    MAX-ACCESS  read-write
    STATUS   current
    DESCRIPTION "Alarm of rectifier62 Enabled(1) or Disabled (0)"
    ::= {psRelay3Masks 221}

r3VBV63Alarm OBJECT-TYPE
    SYNTAX   INTEGER{disabled(0), enabled(1)}
    MAX-ACCESS  read-write
    STATUS   current
    DESCRIPTION "Alarm of rectifier63 Enabled(1) or Disabled (0)"
    ::= {psRelay3Masks 222}

r3VBV64Alarm OBJECT-TYPE
    SYNTAX   INTEGER{disabled(0), enabled(1)}
    MAX-ACCESS  read-write
    STATUS   current
    DESCRIPTION "Alarm of rectifier64 Enabled(1) or Disabled (0)"
    ::= {psRelay3Masks 223}

r3VBV65Alarm OBJECT-TYPE
    SYNTAX   INTEGER{disabled(0), enabled(1)}
    MAX-ACCESS  read-write
    STATUS   current
    DESCRIPTION "Alarm of rectifier65 Enabled(1) or Disabled (0)"
    ::= {psRelay3Masks 224}

r3VBV66Alarm OBJECT-TYPE
    SYNTAX   INTEGER{disabled(0), enabled(1)}
    MAX-ACCESS  read-write
    STATUS   current
    DESCRIPTION "Alarm of rectifier66 Enabled(1) or Disabled (0)"
    ::= {psRelay3Masks 225}

r3VBV67Alarm OBJECT-TYPE
    SYNTAX   INTEGER{disabled(0), enabled(1)}
    MAX-ACCESS  read-write
    STATUS   current
    DESCRIPTION "Alarm of rectifier67 Enabled(1) or Disabled (0)"
    ::= {psRelay3Masks 226}

r3VBV68Alarm OBJECT-TYPE
    SYNTAX   INTEGER{disabled(0), enabled(1)}
    MAX-ACCESS  read-write
    STATUS   current
    DESCRIPTION "Alarm of rectifier68 Enabled(1) or Disabled (0)"
    ::= {psRelay3Masks 227}

r3VBV69Alarm OBJECT-TYPE
    SYNTAX   INTEGER{disabled(0), enabled(1)}
    MAX-ACCESS  read-write
    STATUS   current
    DESCRIPTION "Alarm of rectifier69 Enabled(1) or Disabled (0)"
    ::= {psRelay3Masks 228}

r3VBV70Alarm OBJECT-TYPE
    SYNTAX   INTEGER{disabled(0), enabled(1)}
    MAX-ACCESS  read-write
    STATUS   current
    DESCRIPTION "Alarm of rectifier70 Enabled(1) or Disabled (0)"
    ::= {psRelay3Masks 229}

r3VBV71Alarm OBJECT-TYPE
    SYNTAX   INTEGER{disabled(0), enabled(1)}
    MAX-ACCESS  read-write
    STATUS   current
    DESCRIPTION "Alarm of rectifier71 Enabled(1) or Disabled (0)"
    ::= {psRelay3Masks 230}

r3VBV72Alarm OBJECT-TYPE
    SYNTAX   INTEGER{disabled(0), enabled(1)}
    MAX-ACCESS  read-write
    STATUS   current
    DESCRIPTION "Alarm of rectifier72 Enabled(1) or Disabled (0)"
    ::= {psRelay3Masks 231}

r3VBV73Alarm OBJECT-TYPE
    SYNTAX   INTEGER{disabled(0), enabled(1)}
    MAX-ACCESS  read-write
    STATUS   current
    DESCRIPTION "Alarm of rectifier73 Enabled(1) or Disabled (0)"
    ::= {psRelay3Masks 232}

r3VBV74Alarm OBJECT-TYPE
    SYNTAX   INTEGER{disabled(0), enabled(1)}
    MAX-ACCESS  read-write
    STATUS   current
    DESCRIPTION "Alarm of rectifier74 Enabled(1) or Disabled (0)"
    ::= {psRelay3Masks 233}

r3VBV75Alarm OBJECT-TYPE
    SYNTAX   INTEGER{disabled(0), enabled(1)}
    MAX-ACCESS  read-write
    STATUS   current
    DESCRIPTION "Alarm of rectifier75 Enabled(1) or Disabled (0)"
    ::= {psRelay3Masks 234}

r3VBV76Alarm OBJECT-TYPE
    SYNTAX   INTEGER{disabled(0), enabled(1)}
    MAX-ACCESS  read-write
    STATUS   current
    DESCRIPTION "Alarm of rectifier76 Enabled(1) or Disabled (0)"
    ::= {psRelay3Masks 235}

r3VBV77Alarm OBJECT-TYPE
    SYNTAX   INTEGER{disabled(0), enabled(1)}
    MAX-ACCESS  read-write
    STATUS   current
    DESCRIPTION "Alarm of rectifier77 Enabled(1) or Disabled (0)"
    ::= {psRelay3Masks 236}

r3VBV78Alarm OBJECT-TYPE
    SYNTAX   INTEGER{disabled(0), enabled(1)}
    MAX-ACCESS  read-write
    STATUS   current
    DESCRIPTION "Alarm of rectifier78 Enabled(1) or Disabled (0)"
    ::= {psRelay3Masks 237}

r3VBV79Alarm OBJECT-TYPE
    SYNTAX   INTEGER{disabled(0), enabled(1)}
    MAX-ACCESS  read-write
    STATUS   current
    DESCRIPTION "Alarm of rectifier79 Enabled(1) or Disabled (0)"
    ::= {psRelay3Masks 238}

r3VBV80Alarm OBJECT-TYPE
    SYNTAX   INTEGER{disabled(0), enabled(1)}
    MAX-ACCESS  read-write
    STATUS   current
    DESCRIPTION "Alarm of rectifier80 Enabled(1) or Disabled (0)"
    ::= {psRelay3Masks 239}

r3VBV81Alarm OBJECT-TYPE
    SYNTAX   INTEGER{disabled(0), enabled(1)}
    MAX-ACCESS  read-write
    STATUS   current
    DESCRIPTION "Alarm of rectifier81 Enabled(1) or Disabled (0)"
    ::= {psRelay3Masks 240}

r3VBV82Alarm OBJECT-TYPE
    SYNTAX   INTEGER{disabled(0), enabled(1)}
    MAX-ACCESS  read-write
    STATUS   current
    DESCRIPTION "Alarm of rectifier82 Enabled(1) or Disabled (0)"
    ::= {psRelay3Masks 241}

r3VBV83Alarm OBJECT-TYPE
    SYNTAX   INTEGER{disabled(0), enabled(1)}
    MAX-ACCESS  read-write
    STATUS   current
    DESCRIPTION "Alarm of rectifier83 Enabled(1) or Disabled (0)"
    ::= {psRelay3Masks 242}

r3VBV84Alarm OBJECT-TYPE
    SYNTAX   INTEGER{disabled(0), enabled(1)}
    MAX-ACCESS  read-write
    STATUS   current
    DESCRIPTION "Alarm of rectifier84 Enabled(1) or Disabled (0)"
    ::= {psRelay3Masks 243}

r3VBV85Alarm OBJECT-TYPE
    SYNTAX   INTEGER{disabled(0), enabled(1)}
    MAX-ACCESS  read-write
    STATUS   current
    DESCRIPTION "Alarm of rectifier85 Enabled(1) or Disabled (0)"
    ::= {psRelay3Masks 244}

r3VBV86Alarm OBJECT-TYPE
    SYNTAX   INTEGER{disabled(0), enabled(1)}
    MAX-ACCESS  read-write
    STATUS   current
    DESCRIPTION "Alarm of rectifier86 Enabled(1) or Disabled (0)"
    ::= {psRelay3Masks 245}

r3VBV87Alarm OBJECT-TYPE
    SYNTAX   INTEGER{disabled(0), enabled(1)}
    MAX-ACCESS  read-write
    STATUS   current
    DESCRIPTION "Alarm of rectifier87 Enabled(1) or Disabled (0)"
    ::= {psRelay3Masks 246}

r3VBV88Alarm OBJECT-TYPE
    SYNTAX   INTEGER{disabled(0), enabled(1)}
    MAX-ACCESS  read-write
    STATUS   current
    DESCRIPTION "Alarm of rectifier88 Enabled(1) or Disabled (0)"
    ::= {psRelay3Masks 247}

r3VBV89Alarm OBJECT-TYPE
    SYNTAX   INTEGER{disabled(0), enabled(1)}
    MAX-ACCESS  read-write
    STATUS   current
    DESCRIPTION "Alarm of rectifier89 Enabled(1) or Disabled (0)"
    ::= {psRelay3Masks 248}

r3VBV90Alarm OBJECT-TYPE
    SYNTAX   INTEGER{disabled(0), enabled(1)}
    MAX-ACCESS  read-write
    STATUS   current
    DESCRIPTION "Alarm of rectifier90 Enabled(1) or Disabled (0)"
    ::= {psRelay3Masks 249}

r3VBV91Alarm OBJECT-TYPE
    SYNTAX   INTEGER{disabled(0), enabled(1)}
    MAX-ACCESS  read-write
    STATUS   current
    DESCRIPTION "Alarm of rectifier91 Enabled(1) or Disabled (0)"
    ::= {psRelay3Masks 250}

r3VBV92Alarm OBJECT-TYPE
    SYNTAX   INTEGER{disabled(0), enabled(1)}
    MAX-ACCESS  read-write
    STATUS   current
    DESCRIPTION "Alarm of rectifier92 Enabled(1) or Disabled (0)"
    ::= {psRelay3Masks 251}

r3VBV93Alarm OBJECT-TYPE
    SYNTAX   INTEGER{disabled(0), enabled(1)}
    MAX-ACCESS  read-write
    STATUS   current
    DESCRIPTION "Alarm of rectifier93 Enabled(1) or Disabled (0)"
    ::= {psRelay3Masks 252}

r3VBV94Alarm OBJECT-TYPE
    SYNTAX   INTEGER{disabled(0), enabled(1)}
    MAX-ACCESS  read-write
    STATUS   current
    DESCRIPTION "Alarm of rectifier94 Enabled(1) or Disabled (0)"
    ::= {psRelay3Masks 253}

r3VBV95Alarm OBJECT-TYPE
    SYNTAX   INTEGER{disabled(0), enabled(1)}
    MAX-ACCESS  read-write
    STATUS   current
    DESCRIPTION "Alarm of rectifier95 Enabled(1) or Disabled (0)"
    ::= {psRelay3Masks 254}

r3VBV96Alarm OBJECT-TYPE
    SYNTAX   INTEGER{disabled(0), enabled(1)}
    MAX-ACCESS  read-write
    STATUS   current
    DESCRIPTION "Alarm of rectifier96 Enabled(1) or Disabled (0)"
    ::= {psRelay3Masks 255}

r3VBV97Alarm OBJECT-TYPE
    SYNTAX   INTEGER{disabled(0), enabled(1)}
    MAX-ACCESS  read-write
    STATUS   current
    DESCRIPTION "Alarm of rectifier97 Enabled(1) or Disabled (0)"
    ::= {psRelay3Masks 256}

r3VBV98Alarm OBJECT-TYPE
    SYNTAX   INTEGER{disabled(0), enabled(1)}
    MAX-ACCESS  read-write
    STATUS   current
    DESCRIPTION "Alarm of rectifier98 Enabled(1) or Disabled (0)"
    ::= {psRelay3Masks 257}

r3VBV99Alarm OBJECT-TYPE
    SYNTAX   INTEGER{disabled(0), enabled(1)}
    MAX-ACCESS  read-write
    STATUS   current
    DESCRIPTION "Alarm of rectifier99 Enabled(1) or Disabled (0)"
    ::= {psRelay3Masks 258}

r3VBV100Alarm OBJECT-TYPE
    SYNTAX   INTEGER{disabled(0), enabled(1)}
    MAX-ACCESS  read-write
    STATUS   current
    DESCRIPTION "Alarm of rectifier100 Enabled(1) or Disabled (0)"
    ::= {psRelay3Masks 259}

r3VBV101Alarm OBJECT-TYPE
    SYNTAX   INTEGER{disabled(0), enabled(1)}
    MAX-ACCESS  read-write
    STATUS   current
    DESCRIPTION "Alarm of rectifier101 Enabled(1) or Disabled (0)"
    ::= {psRelay3Masks 260}

r3VBV102Alarm OBJECT-TYPE
    SYNTAX   INTEGER{disabled(0), enabled(1)}
    MAX-ACCESS  read-write
    STATUS   current
    DESCRIPTION "Alarm of rectifier102 Enabled(1) or Disabled (0)"
    ::= {psRelay3Masks 261}

r3VBV103Alarm OBJECT-TYPE
    SYNTAX   INTEGER{disabled(0), enabled(1)}
    MAX-ACCESS  read-write
    STATUS   current
    DESCRIPTION "Alarm of rectifier103 Enabled(1) or Disabled (0)"
    ::= {psRelay3Masks 262}

r3VBV104Alarm OBJECT-TYPE
    SYNTAX   INTEGER{disabled(0), enabled(1)}
    MAX-ACCESS  read-write
    STATUS   current
    DESCRIPTION "Alarm of rectifier104 Enabled(1) or Disabled (0)"
    ::= {psRelay3Masks 263}

r3VBV105Alarm OBJECT-TYPE
    SYNTAX   INTEGER{disabled(0), enabled(1)}
    MAX-ACCESS  read-write
    STATUS   current
    DESCRIPTION "Alarm of rectifier105 Enabled(1) or Disabled (0)"
    ::= {psRelay3Masks 264}

r3VBV106Alarm OBJECT-TYPE
    SYNTAX   INTEGER{disabled(0), enabled(1)}
    MAX-ACCESS  read-write
    STATUS   current
    DESCRIPTION "Alarm of rectifier106 Enabled(1) or Disabled (0)"
    ::= {psRelay3Masks 265}

r3VBV107Alarm OBJECT-TYPE
    SYNTAX   INTEGER{disabled(0), enabled(1)}
    MAX-ACCESS  read-write
    STATUS   current
    DESCRIPTION "Alarm of rectifier107 Enabled(1) or Disabled (0)"
    ::= {psRelay3Masks 266}

r3VBV108Alarm OBJECT-TYPE
    SYNTAX   INTEGER{disabled(0), enabled(1)}
    MAX-ACCESS  read-write
    STATUS   current
    DESCRIPTION "Alarm of rectifier108 Enabled(1) or Disabled (0)"
    ::= {psRelay3Masks 267}

r3VBV109Alarm OBJECT-TYPE
    SYNTAX   INTEGER{disabled(0), enabled(1)}
    MAX-ACCESS  read-write
    STATUS   current
    DESCRIPTION "Alarm of rectifier109 Enabled(1) or Disabled (0)"
    ::= {psRelay3Masks 268}

r3VBV110Alarm OBJECT-TYPE
    SYNTAX   INTEGER{disabled(0), enabled(1)}
    MAX-ACCESS  read-write
    STATUS   current
    DESCRIPTION "Alarm of rectifier110 Enabled(1) or Disabled (0)"
    ::= {psRelay3Masks 269}

r3VBV111Alarm OBJECT-TYPE
    SYNTAX   INTEGER{disabled(0), enabled(1)}
    MAX-ACCESS  read-write
    STATUS   current
    DESCRIPTION "Alarm of rectifier111 Enabled(1) or Disabled (0)"
    ::= {psRelay3Masks 270}

r3VBV112Alarm OBJECT-TYPE
    SYNTAX   INTEGER{disabled(0), enabled(1)}
    MAX-ACCESS  read-write
    STATUS   current
    DESCRIPTION "Alarm of rectifier112 Enabled(1) or Disabled (0)"
    ::= {psRelay3Masks 271}

r3VBV113Alarm OBJECT-TYPE
    SYNTAX   INTEGER{disabled(0), enabled(1)}
    MAX-ACCESS  read-write
    STATUS   current
    DESCRIPTION "Alarm of rectifier113 Enabled(1) or Disabled (0)"
    ::= {psRelay3Masks 272}

r3VBV114Alarm OBJECT-TYPE
    SYNTAX   INTEGER{disabled(0), enabled(1)}
    MAX-ACCESS  read-write
    STATUS   current
    DESCRIPTION "Alarm of rectifier114 Enabled(1) or Disabled (0)"
    ::= {psRelay3Masks 273}

r3VBV115Alarm OBJECT-TYPE
    SYNTAX   INTEGER{disabled(0), enabled(1)}
    MAX-ACCESS  read-write
    STATUS   current
    DESCRIPTION "Alarm of rectifier115 Enabled(1) or Disabled (0)"
    ::= {psRelay3Masks 274}

r3VBV116Alarm OBJECT-TYPE
    SYNTAX   INTEGER{disabled(0), enabled(1)}
    MAX-ACCESS  read-write
    STATUS   current
    DESCRIPTION "Alarm of rectifier116 Enabled(1) or Disabled (0)"
    ::= {psRelay3Masks 275}

r3VBV117Alarm OBJECT-TYPE
    SYNTAX   INTEGER{disabled(0), enabled(1)}
    MAX-ACCESS  read-write
    STATUS   current
    DESCRIPTION "Alarm of rectifier117 Enabled(1) or Disabled (0)"
    ::= {psRelay3Masks 276}

r3VBV118Alarm OBJECT-TYPE
    SYNTAX   INTEGER{disabled(0), enabled(1)}
    MAX-ACCESS  read-write
    STATUS   current
    DESCRIPTION "Alarm of rectifier118 Enabled(1) or Disabled (0)"
    ::= {psRelay3Masks 277}

r3VBV119Alarm OBJECT-TYPE
    SYNTAX   INTEGER{disabled(0), enabled(1)}
    MAX-ACCESS  read-write
    STATUS   current
    DESCRIPTION "Alarm of rectifier119 Enabled(1) or Disabled (0)"
    ::= {psRelay3Masks 278}

r3VBV120Alarm OBJECT-TYPE
    SYNTAX   INTEGER{disabled(0), enabled(1)}
    MAX-ACCESS  read-write
    STATUS   current
    DESCRIPTION "Alarm of rectifier120 Enabled(1) or Disabled (0)"
    ::= {psRelay3Masks 279}

r3VBV121Alarm OBJECT-TYPE
    SYNTAX   INTEGER{disabled(0), enabled(1)}
    MAX-ACCESS  read-write
    STATUS   current
    DESCRIPTION "Alarm of rectifier121 Enabled(1) or Disabled (0)"
    ::= {psRelay3Masks 280}

r3VBV122Alarm OBJECT-TYPE
    SYNTAX   INTEGER{disabled(0), enabled(1)}
    MAX-ACCESS  read-write
    STATUS   current
    DESCRIPTION "Alarm of rectifier122 Enabled(1) or Disabled (0)"
    ::= {psRelay3Masks 281}

r3VBV123Alarm OBJECT-TYPE
    SYNTAX   INTEGER{disabled(0), enabled(1)}
    MAX-ACCESS  read-write
    STATUS   current
    DESCRIPTION "Alarm of rectifier123 Enabled(1) or Disabled (0)"
    ::= {psRelay3Masks 282}

r3VBV124Alarm OBJECT-TYPE
    SYNTAX   INTEGER{disabled(0), enabled(1)}
    MAX-ACCESS  read-write
    STATUS   current
    DESCRIPTION "Alarm of rectifier124 Enabled(1) or Disabled (0)"
    ::= {psRelay3Masks 283}

r3VBV125Alarm OBJECT-TYPE
    SYNTAX   INTEGER{disabled(0), enabled(1)}
    MAX-ACCESS  read-write
    STATUS   current
    DESCRIPTION "Alarm of rectifier125 Enabled(1) or Disabled (0)"
    ::= {psRelay3Masks 284}

r3VBV126Alarm OBJECT-TYPE
    SYNTAX   INTEGER{disabled(0), enabled(1)}
    MAX-ACCESS  read-write
    STATUS   current
    DESCRIPTION "Alarm of rectifier126 Enabled(1) or Disabled (0)"
    ::= {psRelay3Masks 285}

r3VBV127Alarm OBJECT-TYPE
    SYNTAX   INTEGER{disabled(0), enabled(1)}
    MAX-ACCESS  read-write
    STATUS   current
    DESCRIPTION "Alarm of rectifier127 Enabled(1) or Disabled (0)"
    ::= {psRelay3Masks 286}

r3VBV128Alarm OBJECT-TYPE
    SYNTAX   INTEGER{disabled(0), enabled(1)}
    MAX-ACCESS  read-write
    STATUS   current
    DESCRIPTION "Alarm of rectifier128 Enabled(1) or Disabled (0)"
    ::= {psRelay3Masks 287}

r3VBV129Alarm OBJECT-TYPE
    SYNTAX   INTEGER{disabled(0), enabled(1)}
    MAX-ACCESS  read-write
    STATUS   current
    DESCRIPTION "Alarm of rectifier129 Enabled(1) or Disabled (0)"
    ::= {psRelay3Masks 288}

r3VBV130Alarm OBJECT-TYPE
    SYNTAX   INTEGER{disabled(0), enabled(1)}
    MAX-ACCESS  read-write
    STATUS   current
    DESCRIPTION "Alarm of rectifier130 Enabled(1) or Disabled (0)"
    ::= {psRelay3Masks 289}

r3VBV131Alarm OBJECT-TYPE
    SYNTAX   INTEGER{disabled(0), enabled(1)}
    MAX-ACCESS  read-write
    STATUS   current
    DESCRIPTION "Alarm of rectifier131 Enabled(1) or Disabled (0)"
    ::= {psRelay3Masks 290}

r3VBV132Alarm OBJECT-TYPE
    SYNTAX   INTEGER{disabled(0), enabled(1)}
    MAX-ACCESS  read-write
    STATUS   current
    DESCRIPTION "Alarm of rectifier132 Enabled(1) or Disabled (0)"
    ::= {psRelay3Masks 291}

r3VBV133Alarm OBJECT-TYPE
    SYNTAX   INTEGER{disabled(0), enabled(1)}
    MAX-ACCESS  read-write
    STATUS   current
    DESCRIPTION "Alarm of rectifier133 Enabled(1) or Disabled (0)"
    ::= {psRelay3Masks 292}

r3VBV134Alarm OBJECT-TYPE
    SYNTAX   INTEGER{disabled(0), enabled(1)}
    MAX-ACCESS  read-write
    STATUS   current
    DESCRIPTION "Alarm of rectifier134 Enabled(1) or Disabled (0)"
    ::= {psRelay3Masks 293}

r3VBV135Alarm OBJECT-TYPE
    SYNTAX   INTEGER{disabled(0), enabled(1)}
    MAX-ACCESS  read-write
    STATUS   current
    DESCRIPTION "Alarm of rectifier135 Enabled(1) or Disabled (0)"
    ::= {psRelay3Masks 294}

r3VBV136Alarm OBJECT-TYPE
    SYNTAX   INTEGER{disabled(0), enabled(1)}
    MAX-ACCESS  read-write
    STATUS   current
    DESCRIPTION "Alarm of rectifier136 Enabled(1) or Disabled (0)"
    ::= {psRelay3Masks 295}

r3VBV137Alarm OBJECT-TYPE
    SYNTAX   INTEGER{disabled(0), enabled(1)}
    MAX-ACCESS  read-write
    STATUS   current
    DESCRIPTION "Alarm of rectifier137 Enabled(1) or Disabled (0)"
    ::= {psRelay3Masks 296}

r3VBV138Alarm OBJECT-TYPE
    SYNTAX   INTEGER{disabled(0), enabled(1)}
    MAX-ACCESS  read-write
    STATUS   current
    DESCRIPTION "Alarm of rectifier138 Enabled(1) or Disabled (0)"
    ::= {psRelay3Masks 297}

r3VBV139Alarm OBJECT-TYPE
    SYNTAX   INTEGER{disabled(0), enabled(1)}
    MAX-ACCESS  read-write
    STATUS   current
    DESCRIPTION "Alarm of rectifier139 Enabled(1) or Disabled (0)"
    ::= {psRelay3Masks 298}

r3VBV140Alarm OBJECT-TYPE
    SYNTAX   INTEGER{disabled(0), enabled(1)}
    MAX-ACCESS  read-write
    STATUS   current
    DESCRIPTION "Alarm of rectifier140 Enabled(1) or Disabled (0)"
    ::= {psRelay3Masks 299}

r3VBV141Alarm OBJECT-TYPE
    SYNTAX   INTEGER{disabled(0), enabled(1)}
    MAX-ACCESS  read-write
    STATUS   current
    DESCRIPTION "Alarm of rectifier141 Enabled(1) or Disabled (0)"
    ::= {psRelay3Masks 300}

r3VBV142Alarm OBJECT-TYPE
    SYNTAX   INTEGER{disabled(0), enabled(1)}
    MAX-ACCESS  read-write
    STATUS   current
    DESCRIPTION "Alarm of rectifier142 Enabled(1) or Disabled (0)"
    ::= {psRelay3Masks 301}

r3VBV143Alarm OBJECT-TYPE
    SYNTAX   INTEGER{disabled(0), enabled(1)}
    MAX-ACCESS  read-write
    STATUS   current
    DESCRIPTION "Alarm of rectifier143 Enabled(1) or Disabled (0)"
    ::= {psRelay3Masks 302}

r3VBV144Alarm OBJECT-TYPE
    SYNTAX   INTEGER{disabled(0), enabled(1)}
    MAX-ACCESS  read-write
    STATUS   current
    DESCRIPTION "Alarm of rectifier144 Enabled(1) or Disabled (0)"
    ::= {psRelay3Masks 303}

r3VBV145Alarm OBJECT-TYPE
    SYNTAX   INTEGER{disabled(0), enabled(1)}
    MAX-ACCESS  read-write
    STATUS   current
    DESCRIPTION "Alarm of rectifier145 Enabled(1) or Disabled (0)"
    ::= {psRelay3Masks 304}

r3VBV146Alarm OBJECT-TYPE
    SYNTAX   INTEGER{disabled(0), enabled(1)}
    MAX-ACCESS  read-write
    STATUS   current
    DESCRIPTION "Alarm of rectifier146 Enabled(1) or Disabled (0)"
    ::= {psRelay3Masks 305}

r3VBV147Alarm OBJECT-TYPE
    SYNTAX   INTEGER{disabled(0), enabled(1)}
    MAX-ACCESS  read-write
    STATUS   current
    DESCRIPTION "Alarm of rectifier147 Enabled(1) or Disabled (0)"
    ::= {psRelay3Masks 306}

r3VBV148Alarm OBJECT-TYPE
    SYNTAX   INTEGER{disabled(0), enabled(1)}
    MAX-ACCESS  read-write
    STATUS   current
    DESCRIPTION "Alarm of rectifier148 Enabled(1) or Disabled (0)"
    ::= {psRelay3Masks 307}

r3VBV149Alarm OBJECT-TYPE
    SYNTAX   INTEGER{disabled(0), enabled(1)}
    MAX-ACCESS  read-write
    STATUS   current
    DESCRIPTION "Alarm of rectifier149 Enabled(1) or Disabled (0)"
    ::= {psRelay3Masks 308}

r3VBV150Alarm OBJECT-TYPE
    SYNTAX   INTEGER{disabled(0), enabled(1)}
    MAX-ACCESS  read-write
    STATUS   current
    DESCRIPTION "Alarm of rectifier150 Enabled(1) or Disabled (0)"
    ::= {psRelay3Masks 309}

r3VBV151Alarm OBJECT-TYPE
    SYNTAX   INTEGER{disabled(0), enabled(1)}
    MAX-ACCESS  read-write
    STATUS   current
    DESCRIPTION "Alarm of rectifier151 Enabled(1) or Disabled (0)"
    ::= {psRelay3Masks 310}

r3VBV152Alarm OBJECT-TYPE
    SYNTAX   INTEGER{disabled(0), enabled(1)}
    MAX-ACCESS  read-write
    STATUS   current
    DESCRIPTION "Alarm of rectifier152 Enabled(1) or Disabled (0)"
    ::= {psRelay3Masks 311}

r3VBV153Alarm OBJECT-TYPE
    SYNTAX   INTEGER{disabled(0), enabled(1)}
    MAX-ACCESS  read-write
    STATUS   current
    DESCRIPTION "Alarm of rectifier153 Enabled(1) or Disabled (0)"
    ::= {psRelay3Masks 312}

r3VBV154Alarm OBJECT-TYPE
    SYNTAX   INTEGER{disabled(0), enabled(1)}
    MAX-ACCESS  read-write
    STATUS   current
    DESCRIPTION "Alarm of rectifier154 Enabled(1) or Disabled (0)"
    ::= {psRelay3Masks 313}

r3VBV155Alarm OBJECT-TYPE
    SYNTAX   INTEGER{disabled(0), enabled(1)}
    MAX-ACCESS  read-write
    STATUS   current
    DESCRIPTION "Alarm of rectifier155 Enabled(1) or Disabled (0)"
    ::= {psRelay3Masks 314}

r3VBV156Alarm OBJECT-TYPE
    SYNTAX   INTEGER{disabled(0), enabled(1)}
    MAX-ACCESS  read-write
    STATUS   current
    DESCRIPTION "Alarm of rectifier156 Enabled(1) or Disabled (0)"
    ::= {psRelay3Masks 315}

r3VBV157Alarm OBJECT-TYPE
    SYNTAX   INTEGER{disabled(0), enabled(1)}
    MAX-ACCESS  read-write
    STATUS   current
    DESCRIPTION "Alarm of rectifier157 Enabled(1) or Disabled (0)"
    ::= {psRelay3Masks 316}

r3VBV158Alarm OBJECT-TYPE
    SYNTAX   INTEGER{disabled(0), enabled(1)}
    MAX-ACCESS  read-write
    STATUS   current
    DESCRIPTION "Alarm of rectifier158 Enabled(1) or Disabled (0)"
    ::= {psRelay3Masks 317}

r3VBV159Alarm OBJECT-TYPE
    SYNTAX   INTEGER{disabled(0), enabled(1)}
    MAX-ACCESS  read-write
    STATUS   current
    DESCRIPTION "Alarm of rectifier159 Enabled(1) or Disabled (0)"
    ::= {psRelay3Masks 318}

r3VBV160Alarm OBJECT-TYPE
    SYNTAX   INTEGER{disabled(0), enabled(1)}
    MAX-ACCESS  read-write
    STATUS   current
    DESCRIPTION "Alarm of rectifier160 Enabled(1) or Disabled (0)"
    ::= {psRelay3Masks 319}

r3VBV161Alarm OBJECT-TYPE
    SYNTAX   INTEGER{disabled(0), enabled(1)}
    MAX-ACCESS  read-write
    STATUS   current
    DESCRIPTION "Alarm of rectifier161 Enabled(1) or Disabled (0)"
    ::= {psRelay3Masks 320}

r3VBV162Alarm OBJECT-TYPE
    SYNTAX   INTEGER{disabled(0), enabled(1)}
    MAX-ACCESS  read-write
    STATUS   current
    DESCRIPTION "Alarm of rectifier162 Enabled(1) or Disabled (0)"
    ::= {psRelay3Masks 321}

r3VBV163Alarm OBJECT-TYPE
    SYNTAX   INTEGER{disabled(0), enabled(1)}
    MAX-ACCESS  read-write
    STATUS   current
    DESCRIPTION "Alarm of rectifier163 Enabled(1) or Disabled (0)"
    ::= {psRelay3Masks 322}

r3VBV164Alarm OBJECT-TYPE
    SYNTAX   INTEGER{disabled(0), enabled(1)}
    MAX-ACCESS  read-write
    STATUS   current
    DESCRIPTION "Alarm of rectifier164 Enabled(1) or Disabled (0)"
    ::= {psRelay3Masks 323}

r3VBV165Alarm OBJECT-TYPE
    SYNTAX   INTEGER{disabled(0), enabled(1)}
    MAX-ACCESS  read-write
    STATUS   current
    DESCRIPTION "Alarm of rectifier165 Enabled(1) or Disabled (0)"
    ::= {psRelay3Masks 324}

r3VBV166Alarm OBJECT-TYPE
    SYNTAX   INTEGER{disabled(0), enabled(1)}
    MAX-ACCESS  read-write
    STATUS   current
    DESCRIPTION "Alarm of rectifier166 Enabled(1) or Disabled (0)"
    ::= {psRelay3Masks 325}

r3VBV167Alarm OBJECT-TYPE
    SYNTAX   INTEGER{disabled(0), enabled(1)}
    MAX-ACCESS  read-write
    STATUS   current
    DESCRIPTION "Alarm of rectifier167 Enabled(1) or Disabled (0)"
    ::= {psRelay3Masks 326}

r3VBV168Alarm OBJECT-TYPE
    SYNTAX   INTEGER{disabled(0), enabled(1)}
    MAX-ACCESS  read-write
    STATUS   current
    DESCRIPTION "Alarm of rectifier168 Enabled(1) or Disabled (0)"
    ::= {psRelay3Masks 327}

r3VBV169Alarm OBJECT-TYPE
    SYNTAX   INTEGER{disabled(0), enabled(1)}
    MAX-ACCESS  read-write
    STATUS   current
    DESCRIPTION "Alarm of rectifier169 Enabled(1) or Disabled (0)"
    ::= {psRelay3Masks 328}

r3VBV170Alarm OBJECT-TYPE
    SYNTAX   INTEGER{disabled(0), enabled(1)}
    MAX-ACCESS  read-write
    STATUS   current
    DESCRIPTION "Alarm of rectifier170 Enabled(1) or Disabled (0)"
    ::= {psRelay3Masks 329}

r3VBV171Alarm OBJECT-TYPE
    SYNTAX   INTEGER{disabled(0), enabled(1)}
    MAX-ACCESS  read-write
    STATUS   current
    DESCRIPTION "Alarm of rectifier171 Enabled(1) or Disabled (0)"
    ::= {psRelay3Masks 330}

r3VBV172Alarm OBJECT-TYPE
    SYNTAX   INTEGER{disabled(0), enabled(1)}
    MAX-ACCESS  read-write
    STATUS   current
    DESCRIPTION "Alarm of rectifier172 Enabled(1) or Disabled (0)"
    ::= {psRelay3Masks 331}

r3VBV173Alarm OBJECT-TYPE
    SYNTAX   INTEGER{disabled(0), enabled(1)}
    MAX-ACCESS  read-write
    STATUS   current
    DESCRIPTION "Alarm of rectifier173 Enabled(1) or Disabled (0)"
    ::= {psRelay3Masks 332}

r3VBV174Alarm OBJECT-TYPE
    SYNTAX   INTEGER{disabled(0), enabled(1)}
    MAX-ACCESS  read-write
    STATUS   current
    DESCRIPTION "Alarm of rectifier174 Enabled(1) or Disabled (0)"
    ::= {psRelay3Masks 333}

r3VBV175Alarm OBJECT-TYPE
    SYNTAX   INTEGER{disabled(0), enabled(1)}
    MAX-ACCESS  read-write
    STATUS   current
    DESCRIPTION "Alarm of rectifier175 Enabled(1) or Disabled (0)"
    ::= {psRelay3Masks 334}

r3VBV176Alarm OBJECT-TYPE
    SYNTAX   INTEGER{disabled(0), enabled(1)}
    MAX-ACCESS  read-write
    STATUS   current
    DESCRIPTION "Alarm of rectifier176 Enabled(1) or Disabled (0)"
    ::= {psRelay3Masks 335}

r3VBV177Alarm OBJECT-TYPE
    SYNTAX   INTEGER{disabled(0), enabled(1)}
    MAX-ACCESS  read-write
    STATUS   current
    DESCRIPTION "Alarm of rectifier177 Enabled(1) or Disabled (0)"
    ::= {psRelay3Masks 336}

r3VBV178Alarm OBJECT-TYPE
    SYNTAX   INTEGER{disabled(0), enabled(1)}
    MAX-ACCESS  read-write
    STATUS   current
    DESCRIPTION "Alarm of rectifier178 Enabled(1) or Disabled (0)"
    ::= {psRelay3Masks 337}

r3VBV179Alarm OBJECT-TYPE
    SYNTAX   INTEGER{disabled(0), enabled(1)}
    MAX-ACCESS  read-write
    STATUS   current
    DESCRIPTION "Alarm of rectifier179 Enabled(1) or Disabled (0)"
    ::= {psRelay3Masks 338}

r3VBV180Alarm OBJECT-TYPE
    SYNTAX   INTEGER{disabled(0), enabled(1)}
    MAX-ACCESS  read-write
    STATUS   current
    DESCRIPTION "Alarm of rectifier180 Enabled(1) or Disabled (0)"
    ::= {psRelay3Masks 339}

r3VBVNoReserve OBJECT-TYPE
    SYNTAX   INTEGER{disabled(0), enabled(1)}
    MAX-ACCESS  read-write
    STATUS   current
    DESCRIPTION "Enabled(1) or Disabled (0)"
    ::= {psRelay3Masks 340}

r3VBVHighEfficiency OBJECT-TYPE
    SYNTAX   INTEGER{disabled(0), enabled(1)}
    MAX-ACCESS  read-write
    STATUS   current
    DESCRIPTION "Enabled(1) or Disabled (0)"
    ::= {psRelay3Masks 341}

--PhasesAlarm in psRelay3Masks
r3Phase1Alarm OBJECT-TYPE
    SYNTAX   INTEGER{disabled(0), enabled(1)}
    MAX-ACCESS  read-write
    STATUS   current
    DESCRIPTION "Enabled(1) or Disabled (0)"
    ::= {psRelay3Masks 352}

r3Phase2Alarm OBJECT-TYPE
    SYNTAX   INTEGER{disabled(0), enabled(1)}
    MAX-ACCESS  read-write
    STATUS   current
    DESCRIPTION "Enabled(1) or Disabled (0)"
    ::= {psRelay3Masks 353}

r3Phase3Alarm OBJECT-TYPE
    SYNTAX   INTEGER{disabled(0), enabled(1)}
    MAX-ACCESS  read-write
    STATUS   current
    DESCRIPTION "Enabled(1) or Disabled (0)"
    ::= {psRelay3Masks 354}

r3MainsSensorError OBJECT-TYPE
    SYNTAX   INTEGER{disabled(0), enabled(1)}
    MAX-ACCESS  read-write
    STATUS   current
    DESCRIPTION "Enabled(1) or Disabled (0)"
    ::= {psRelay3Masks 355}

r3LightProtectionAlarm OBJECT-TYPE
    SYNTAX   INTEGER{disabled(0), enabled(1)}
    MAX-ACCESS  read-write
    STATUS   current
    DESCRIPTION "Enabled(1) or Disabled (0)"
    ::= {psRelay3Masks 356}

--Ambience Temperature in psRelay3Masks
r3LowTemperature OBJECT-TYPE
    SYNTAX   INTEGER{disabled(0), enabled(1)}
    MAX-ACCESS  read-write
    STATUS   current
    DESCRIPTION "Enabled(1) or Disabled (0)"
    ::= {psRelay3Masks 384}

r3HighTemperature OBJECT-TYPE
    SYNTAX   INTEGER{disabled(0), enabled(1)}
    MAX-ACCESS  read-write
    STATUS   current
    DESCRIPTION "Enabled(1) or Disabled (0)"
    ::= {psRelay3Masks 385}

r3TemperatureSensorError OBJECT-TYPE
    SYNTAX   INTEGER{disabled(0), enabled(1)}
    MAX-ACCESS  read-write
    STATUS   current
    DESCRIPTION "Enabled(1) or Disabled (0)"
    ::= {psRelay3Masks 386}

--DryContacts in psRelay3Masks
r3DryContact1 OBJECT-TYPE
    SYNTAX   INTEGER{disabled(0), enabled(1)}
    MAX-ACCESS  read-write
    STATUS   current
    DESCRIPTION "Enabled(1) or Disabled (0)"
    ::= {psRelay3Masks 416}

r3DryContact2 OBJECT-TYPE
    SYNTAX   INTEGER{disabled(0), enabled(1)}
    MAX-ACCESS  read-write
    STATUS   current
    DESCRIPTION "Enabled(1) or Disabled (0)"
    ::= {psRelay3Masks 417}

r3DryContact3 OBJECT-TYPE
    SYNTAX   INTEGER{disabled(0), enabled(1)}
    MAX-ACCESS  read-write
    STATUS   current
    DESCRIPTION "Enabled(1) or Disabled (0)"
    ::= {psRelay3Masks 418}

r3DryContact4 OBJECT-TYPE
    SYNTAX   INTEGER{disabled(0), enabled(1)}
    MAX-ACCESS  read-write
    STATUS   current
    DESCRIPTION "Enabled(1) or Disabled (0)"
    ::= {psRelay3Masks 419}

r3DryContact5 OBJECT-TYPE
    SYNTAX   INTEGER{disabled(0), enabled(1)}
    MAX-ACCESS  read-write
    STATUS   current
    DESCRIPTION "Enabled(1) or Disabled (0)"
    ::= {psRelay3Masks 420}

r3DryContact6 OBJECT-TYPE
    SYNTAX   INTEGER{disabled(0), enabled(1)}
    MAX-ACCESS  read-write
    STATUS   current
    DESCRIPTION "Enabled(1) or Disabled (0)"
    ::= {psRelay3Masks 421}

r3DryContact7 OBJECT-TYPE
    SYNTAX   INTEGER{disabled(0), enabled(1)}
    MAX-ACCESS  read-write
    STATUS   current
    DESCRIPTION "Enabled(1) or Disabled (0)"
    ::= {psRelay3Masks 422}

r3DryContact8 OBJECT-TYPE
    SYNTAX   INTEGER{disabled(0), enabled(1)}
    MAX-ACCESS  read-write
    STATUS   current
    DESCRIPTION "Enabled(1) or Disabled (0)"
    ::= {psRelay3Masks 423}

r3DryContact9 OBJECT-TYPE
    SYNTAX   INTEGER{disabled(0), enabled(1)}
    MAX-ACCESS  read-write
    STATUS   current
    DESCRIPTION "Enabled(1) or Disabled (0)"
    ::= {psRelay3Masks 424}

r3DryContact10 OBJECT-TYPE
    SYNTAX   INTEGER{disabled(0), enabled(1)}
    MAX-ACCESS  read-write
    STATUS   current
    DESCRIPTION "Enabled(1) or Disabled (0)"
    ::= {psRelay3Masks 425}

r3DryContact11 OBJECT-TYPE
    SYNTAX   INTEGER{disabled(0), enabled(1)}
    MAX-ACCESS  read-write
    STATUS   current
    DESCRIPTION "Enabled(1) or Disabled (0)"
    ::= {psRelay3Masks 426}

r3DryContact12 OBJECT-TYPE
    SYNTAX   INTEGER{disabled(0), enabled(1)}
    MAX-ACCESS  read-write
    STATUS   current
    DESCRIPTION "Enabled(1) or Disabled (0)"
    ::= {psRelay3Masks 427}

r3DryContact13 OBJECT-TYPE
    SYNTAX   INTEGER{disabled(0), enabled(1)}
    MAX-ACCESS  read-write
    STATUS   current
    DESCRIPTION "Enabled(1) or Disabled (0)"
    ::= {psRelay3Masks 428}

r3DryContact14 OBJECT-TYPE
    SYNTAX   INTEGER{disabled(0), enabled(1)}
    MAX-ACCESS  read-write
    STATUS   current
    DESCRIPTION "Enabled(1) or Disabled (0)"
    ::= {psRelay3Masks 429}

r3DryContact15 OBJECT-TYPE
    SYNTAX   INTEGER{disabled(0), enabled(1)}
    MAX-ACCESS  read-write
    STATUS   current
    DESCRIPTION "Enabled(1) or Disabled (0)"
    ::= {psRelay3Masks 430}

r3DryContact16 OBJECT-TYPE
    SYNTAX   INTEGER{disabled(0), enabled(1)}
    MAX-ACCESS  read-write
    STATUS   current
    DESCRIPTION "Enabled(1) or Disabled (0)"
    ::= {psRelay3Masks 431}

-- --------------------------------------

r3BatteryLiIonAlarm OBJECT-TYPE  
    SYNTAX   INTEGER{disabled(0), enabled(1)}
    MAX-ACCESS  read-write
    STATUS   current
    DESCRIPTION "Enabled(1) or Disabled (0)"
    ::= {psRelay3Masks 480}

--нет связи с BMS
r3BatteryBMSComFail OBJECT-TYPE  
    SYNTAX   INTEGER{disabled(0), enabled(1)}
    MAX-ACCESS  read-write
    STATUS   current
    DESCRIPTION "Enabled(1) or Disabled (0)"
    ::= {psRelay3Masks 481}

-- --------------------------------------

--InternalErrors in psRelay4Masks
r4InternallError OBJECT-TYPE
    SYNTAX   INTEGER{disabled(0), enabled(1)}
    MAX-ACCESS  read-write
    STATUS   current
    DESCRIPTION "Enabled(1) or Disabled (0)"
    ::= {psRelay4Masks 1}

--OutputAlarms in psRelay4Masks
r4LoadUnderVoltageAlarm OBJECT-TYPE
    SYNTAX   INTEGER{disabled(0), enabled(1)}
    MAX-ACCESS  read-write
    STATUS   current
    DESCRIPTION "Enabled(1) or Disabled (0)"
    ::= {psRelay4Masks 32}

r4LoadOverVoltageAlarm OBJECT-TYPE
    SYNTAX   INTEGER{disabled(0), enabled(1)}
    MAX-ACCESS  read-write
    STATUS   current
    DESCRIPTION "Enabled(1) or Disabled (0)"
    ::= {psRelay4Masks 33}

r4Termocompensation OBJECT-TYPE
    SYNTAX   INTEGER{disabled(0), enabled(1)}
    MAX-ACCESS  read-write
    STATUS   current
    DESCRIPTION "Enabled(1) or Disabled (0)"
    ::= {psRelay4Masks 34}

--LoadFuses in psRelay4Masks
r4LoadFuses1 OBJECT-TYPE
    SYNTAX   INTEGER{disabled(0), enabled(1)}
    MAX-ACCESS  read-write
    STATUS   current
    DESCRIPTION "Enabled(1) or Disabled (0)"
    ::= {psRelay4Masks 35}

r4LoadFuses2 OBJECT-TYPE
    SYNTAX   INTEGER{disabled(0), enabled(1)}
    MAX-ACCESS  read-write
    STATUS   current
    DESCRIPTION "Enabled(1) or Disabled (0)"
    ::= {psRelay4Masks 36}

r4LoadFuses3 OBJECT-TYPE
    SYNTAX   INTEGER{disabled(0), enabled(1)}
    MAX-ACCESS  read-write
    STATUS   current
    DESCRIPTION "Enabled(1) or Disabled (0)"
    ::= {psRelay4Masks 37}

r4LoadFuses4 OBJECT-TYPE
    SYNTAX   INTEGER{disabled(0), enabled(1)}
    MAX-ACCESS  read-write
    STATUS   current
    DESCRIPTION "Enabled(1) or Disabled (0)"
    ::= {psRelay4Masks 38}

r4LoadFuses5 OBJECT-TYPE
    SYNTAX   INTEGER{disabled(0), enabled(1)}
    MAX-ACCESS  read-write
    STATUS   current
    DESCRIPTION "Enabled(1) or Disabled (0)"
    ::= {psRelay4Masks 39}

r4LoadFuses6 OBJECT-TYPE
    SYNTAX   INTEGER{disabled(0), enabled(1)}
    MAX-ACCESS  read-write
    STATUS   current
    DESCRIPTION "Enabled(1) or Disabled (0)"
    ::= {psRelay4Masks 40}

r4LoadFuses7 OBJECT-TYPE
    SYNTAX   INTEGER{disabled(0), enabled(1)}
    MAX-ACCESS  read-write
    STATUS   current
    DESCRIPTION "Enabled(1) or Disabled (0)"
    ::= {psRelay4Masks 41}

r4LoadFuses8 OBJECT-TYPE
    SYNTAX   INTEGER{disabled(0), enabled(1)}
    MAX-ACCESS  read-write
    STATUS   current
    DESCRIPTION "Enabled(1) or Disabled (0)"
    ::= {psRelay4Masks 42}

r4LoadFuses9 OBJECT-TYPE
    SYNTAX   INTEGER{disabled(0), enabled(1)}
    MAX-ACCESS  read-write
    STATUS   current
    DESCRIPTION "Enabled(1) or Disabled (0)"
    ::= {psRelay4Masks 43}

r4LoadFuses10 OBJECT-TYPE
    SYNTAX   INTEGER{disabled(0), enabled(1)}
    MAX-ACCESS  read-write
    STATUS   current
    DESCRIPTION "Enabled(1) or Disabled (0)"
    ::= {psRelay4Masks 44}

r4LoadFuses11 OBJECT-TYPE
    SYNTAX   INTEGER{disabled(0), enabled(1)}
    MAX-ACCESS  read-write
    STATUS   current
    DESCRIPTION "Enabled(1) or Disabled (0)"
    ::= {psRelay4Masks 45}

r4LoadFuses12 OBJECT-TYPE
    SYNTAX   INTEGER{disabled(0), enabled(1)}
    MAX-ACCESS  read-write
    STATUS   current
    DESCRIPTION "Enabled(1) or Disabled (0)"
    ::= {psRelay4Masks 46}

r4LoadFuses13 OBJECT-TYPE
    SYNTAX   INTEGER{disabled(0), enabled(1)}
    MAX-ACCESS  read-write
    STATUS   current
    DESCRIPTION "Enabled(1) or Disabled (0)"
    ::= {psRelay4Masks 47}

r4LoadFuses14 OBJECT-TYPE
    SYNTAX   INTEGER{disabled(0), enabled(1)}
    MAX-ACCESS  read-write
    STATUS   current
    DESCRIPTION "Enabled(1) or Disabled (0)"
    ::= {psRelay4Masks 48}

r4LoadFuses15 OBJECT-TYPE
    SYNTAX   INTEGER{disabled(0), enabled(1)}
    MAX-ACCESS  read-write
    STATUS   current
    DESCRIPTION "Enabled(1) or Disabled (0)"
    ::= {psRelay4Masks 49}

r4LoadFuses16 OBJECT-TYPE
    SYNTAX   INTEGER{disabled(0), enabled(1)}
    MAX-ACCESS  read-write
    STATUS   current
    DESCRIPTION "Enabled(1) or Disabled (0)"
    ::= {psRelay4Masks 50}

r4LoadFuses17 OBJECT-TYPE
    SYNTAX   INTEGER{disabled(0), enabled(1)}
    MAX-ACCESS  read-write
    STATUS   current
    DESCRIPTION "Enabled(1) or Disabled (0)"
    ::= {psRelay4Masks 51}

r4LoadFuses18 OBJECT-TYPE
    SYNTAX   INTEGER{disabled(0), enabled(1)}
    MAX-ACCESS  read-write
    STATUS   current
    DESCRIPTION "Enabled(1) or Disabled (0)"
    ::= {psRelay4Masks 52}

r4LoadFuses19 OBJECT-TYPE
    SYNTAX   INTEGER{disabled(0), enabled(1)}
    MAX-ACCESS  read-write
    STATUS   current
    DESCRIPTION "Enabled(1) or Disabled (0)"
    ::= {psRelay4Masks 53}

r4LoadFuses20 OBJECT-TYPE
    SYNTAX   INTEGER{disabled(0), enabled(1)}
    MAX-ACCESS  read-write
    STATUS   current
    DESCRIPTION "Enabled(1) or Disabled (0)"
    ::= {psRelay4Masks 54}

r4LoadFuses21 OBJECT-TYPE
    SYNTAX   INTEGER{disabled(0), enabled(1)}
    MAX-ACCESS  read-write
    STATUS   current
    DESCRIPTION "Enabled(1) or Disabled (0)"
    ::= {psRelay4Masks 55}

r4LoadFuses22 OBJECT-TYPE
    SYNTAX   INTEGER{disabled(0), enabled(1)}
    MAX-ACCESS  read-write
    STATUS   current
    DESCRIPTION "Enabled(1) or Disabled (0)"
    ::= {psRelay4Masks 56}

r4LoadFuses23 OBJECT-TYPE
    SYNTAX   INTEGER{disabled(0), enabled(1)}
    MAX-ACCESS  read-write
    STATUS   current
    DESCRIPTION "Enabled(1) or Disabled (0)"
    ::= {psRelay4Masks 57}

r4LoadFuses24 OBJECT-TYPE
    SYNTAX   INTEGER{disabled(0), enabled(1)}
    MAX-ACCESS  read-write
    STATUS   current
    DESCRIPTION "Enabled(1) or Disabled (0)"
    ::= {psRelay4Masks 58}

r4LoadFuses25 OBJECT-TYPE
    SYNTAX   INTEGER{disabled(0), enabled(1)}
    MAX-ACCESS  read-write
    STATUS   current
    DESCRIPTION "Enabled(1) or Disabled (0)"
    ::= {psRelay4Masks 59}

r4LoadFuses26 OBJECT-TYPE
    SYNTAX   INTEGER{disabled(0), enabled(1)}
    MAX-ACCESS  read-write
    STATUS   current
    DESCRIPTION "Enabled(1) or Disabled (0)"
    ::= {psRelay4Masks 60}

r4LoadFuses27 OBJECT-TYPE
    SYNTAX   INTEGER{disabled(0), enabled(1)}
    MAX-ACCESS  read-write
    STATUS   current
    DESCRIPTION "Enabled(1) or Disabled (0)"
    ::= {psRelay4Masks 61}

r4LoadFuses28 OBJECT-TYPE
    SYNTAX   INTEGER{disabled(0), enabled(1)}
    MAX-ACCESS  read-write
    STATUS   current
    DESCRIPTION "Enabled(1) or Disabled (0)"
    ::= {psRelay4Masks 62}

r4LoadFuses29 OBJECT-TYPE
    SYNTAX   INTEGER{disabled(0), enabled(1)}
    MAX-ACCESS  read-write
    STATUS   current
    DESCRIPTION "Enabled(1) or Disabled (0)"
    ::= {psRelay4Masks 63}

r4LoadFuses30 OBJECT-TYPE
    SYNTAX   INTEGER{disabled(0), enabled(1)}
    MAX-ACCESS  read-write
    STATUS   current
    DESCRIPTION "Enabled(1) or Disabled (0)"
    ::= {psRelay4Masks 64}

r4LoadFuses31 OBJECT-TYPE
    SYNTAX   INTEGER{disabled(0), enabled(1)}
    MAX-ACCESS  read-write
    STATUS   current
    DESCRIPTION "Enabled(1) or Disabled (0)"
    ::= {psRelay4Masks 65}

r4LoadFuses32 OBJECT-TYPE
    SYNTAX   INTEGER{disabled(0), enabled(1)}
    MAX-ACCESS  read-write
    STATUS   current
    DESCRIPTION "Enabled(1) or Disabled (0)"
    ::= {psRelay4Masks 66}

r4LoadFuses33 OBJECT-TYPE
    SYNTAX   INTEGER{disabled(0), enabled(1)}
    MAX-ACCESS  read-write
    STATUS   current
    DESCRIPTION "Enabled(1) or Disabled (0)"
    ::= {psRelay4Masks 67}

r4LoadFuses34 OBJECT-TYPE
    SYNTAX   INTEGER{disabled(0), enabled(1)}
    MAX-ACCESS  read-write
    STATUS   current
    DESCRIPTION "Enabled(1) or Disabled (0)"
    ::= {psRelay4Masks 68}

r4LoadFuses35 OBJECT-TYPE
    SYNTAX   INTEGER{disabled(0), enabled(1)}
    MAX-ACCESS  read-write
    STATUS   current
    DESCRIPTION "Enabled(1) or Disabled (0)"
    ::= {psRelay4Masks 69}

r4LoadFuses36 OBJECT-TYPE
    SYNTAX   INTEGER{disabled(0), enabled(1)}
    MAX-ACCESS  read-write
    STATUS   current
    DESCRIPTION "Enabled(1) or Disabled (0)"
    ::= {psRelay4Masks 70}

r4LoadFuses37 OBJECT-TYPE
    SYNTAX   INTEGER{disabled(0), enabled(1)}
    MAX-ACCESS  read-write
    STATUS   current
    DESCRIPTION "Enabled(1) or Disabled (0)"
    ::= {psRelay4Masks 71}

r4LoadFuses38 OBJECT-TYPE
    SYNTAX   INTEGER{disabled(0), enabled(1)}
    MAX-ACCESS  read-write
    STATUS   current
    DESCRIPTION "Enabled(1) or Disabled (0)"
    ::= {psRelay4Masks 72}

r4LoadFuses39 OBJECT-TYPE
    SYNTAX   INTEGER{disabled(0), enabled(1)}
    MAX-ACCESS  read-write
    STATUS   current
    DESCRIPTION "Enabled(1) or Disabled (0)"
    ::= {psRelay4Masks 73}

r4LoadFuses40 OBJECT-TYPE
    SYNTAX   INTEGER{disabled(0), enabled(1)}
    MAX-ACCESS  read-write
    STATUS   current
    DESCRIPTION "Enabled(1) or Disabled (0)"
    ::= {psRelay4Masks 74}

r4LoadFuses41 OBJECT-TYPE
    SYNTAX   INTEGER{disabled(0), enabled(1)}
    MAX-ACCESS  read-write
    STATUS   current
    DESCRIPTION "Enabled(1) or Disabled (0)"
    ::= {psRelay4Masks 75}

r4LoadFuses42 OBJECT-TYPE
    SYNTAX   INTEGER{disabled(0), enabled(1)}
    MAX-ACCESS  read-write
    STATUS   current
    DESCRIPTION "Enabled(1) or Disabled (0)"
    ::= {psRelay4Masks 76}

r4LoadFuses43 OBJECT-TYPE
    SYNTAX   INTEGER{disabled(0), enabled(1)}
    MAX-ACCESS  read-write
    STATUS   current
    DESCRIPTION "Enabled(1) or Disabled (0)"
    ::= {psRelay4Masks 77}

r4LoadFuses44 OBJECT-TYPE
    SYNTAX   INTEGER{disabled(0), enabled(1)}
    MAX-ACCESS  read-write
    STATUS   current
    DESCRIPTION "Enabled(1) or Disabled (0)"
    ::= {psRelay4Masks 78}

r4LoadFuses45 OBJECT-TYPE
    SYNTAX   INTEGER{disabled(0), enabled(1)}
    MAX-ACCESS  read-write
    STATUS   current
    DESCRIPTION "Enabled(1) or Disabled (0)"
    ::= {psRelay4Masks 79}

r4LoadFuses46 OBJECT-TYPE
    SYNTAX   INTEGER{disabled(0), enabled(1)}
    MAX-ACCESS  read-write
    STATUS   current
    DESCRIPTION "Enabled(1) or Disabled (0)"
    ::= {psRelay4Masks 80}

r4LoadFuses47 OBJECT-TYPE
    SYNTAX   INTEGER{disabled(0), enabled(1)}
    MAX-ACCESS  read-write
    STATUS   current
    DESCRIPTION "Enabled(1) or Disabled (0)"
    ::= {psRelay4Masks 81}

r4LoadFuses48 OBJECT-TYPE
    SYNTAX   INTEGER{disabled(0), enabled(1)}
    MAX-ACCESS  read-write
    STATUS   current
    DESCRIPTION "Enabled(1) or Disabled (0)"
    ::= {psRelay4Masks 82}

r4LoadFuses49 OBJECT-TYPE
    SYNTAX   INTEGER{disabled(0), enabled(1)}
    MAX-ACCESS  read-write
    STATUS   current
    DESCRIPTION "Enabled(1) or Disabled (0)"
    ::= {psRelay4Masks 83}

r4LoadFuses50 OBJECT-TYPE
    SYNTAX   INTEGER{disabled(0), enabled(1)}
    MAX-ACCESS  read-write
    STATUS   current
    DESCRIPTION "Enabled(1) or Disabled (0)"
    ::= {psRelay4Masks 84}

r4LoadFuses51 OBJECT-TYPE
    SYNTAX   INTEGER{disabled(0), enabled(1)}
    MAX-ACCESS  read-write
    STATUS   current
    DESCRIPTION "Enabled(1) or Disabled (0)"
    ::= {psRelay4Masks 85}

r4LoadFuses52 OBJECT-TYPE
    SYNTAX   INTEGER{disabled(0), enabled(1)}
    MAX-ACCESS  read-write
    STATUS   current
    DESCRIPTION "Enabled(1) or Disabled (0)"
    ::= {psRelay4Masks 86}

r4UKDVAlarm OBJECT-TYPE
    SYNTAX   INTEGER{disabled(0), enabled(1)}
    MAX-ACCESS  read-write
    STATUS   current
    DESCRIPTION "Enabled(1) or Disabled (0)"
    ::= {psRelay4Masks 87}

--Battery Events in psRelay4Masks
r4BatteryDischarge OBJECT-TYPE
    SYNTAX   INTEGER{disabled(0), enabled(1)}
    MAX-ACCESS  read-write
    STATUS   current
    DESCRIPTION "Enabled(1) or Disabled (0)"
    ::= {psRelay4Masks 96}

r4LowBatteryVoltage OBJECT-TYPE
    SYNTAX   INTEGER{disabled(0), enabled(1)}
    MAX-ACCESS  read-write
    STATUS   current
    DESCRIPTION "Enabled(1) or Disabled (0)"
    ::= {psRelay4Masks 97}

r4BatteryCharge OBJECT-TYPE
    SYNTAX   INTEGER{disabled(0), enabled(1)}
    MAX-ACCESS  read-write
    STATUS   current
    DESCRIPTION "Enabled(1) or Disabled (0)"
    ::= {psRelay4Masks 98}

r4BatteryBoost OBJECT-TYPE
    SYNTAX   INTEGER{disabled(0), enabled(1)}
    MAX-ACCESS  read-write
    STATUS   current
    DESCRIPTION "Enabled(1) or Disabled (0)"
    ::= {psRelay4Masks 99}

r4BatteryFloat OBJECT-TYPE
    SYNTAX   INTEGER{disabled(0), enabled(1)}
    MAX-ACCESS  read-write
    STATUS   current
    DESCRIPTION "Enabled(1) or Disabled (0)"
    ::= {psRelay4Masks 100}

r4BatteryEqualize OBJECT-TYPE
    SYNTAX   INTEGER{disabled(0), enabled(1)}
    MAX-ACCESS  read-write
    STATUS   current
    DESCRIPTION "Enabled(1) or Disabled (0)"
    ::= {psRelay4Masks 101}

r4BatteryTest OBJECT-TYPE
    SYNTAX   INTEGER{disabled(0), enabled(1)}
    MAX-ACCESS  read-write
    STATUS   current
    DESCRIPTION "Enabled(1) or Disabled (0)"
    ::= {psRelay4Masks 102}

r4BatteryFuse1Off OBJECT-TYPE
    SYNTAX   INTEGER{disabled(0), enabled(1)}
    MAX-ACCESS  read-write
    STATUS   current
    DESCRIPTION "Enabled(1) or Disabled (0)"
    ::= {psRelay4Masks 103}

r4BatteryFuse2Off OBJECT-TYPE
    SYNTAX   INTEGER{disabled(0), enabled(1)}
    MAX-ACCESS  read-write
    STATUS   current
    DESCRIPTION "Enabled(1) or Disabled (0)"
    ::= {psRelay4Masks 104}

r4BatteryFuse3Off OBJECT-TYPE
    SYNTAX   INTEGER{disabled(0), enabled(1)}
    MAX-ACCESS  read-write
    STATUS   current
    DESCRIPTION "Enabled(1) or Disabled (0)"
    ::= {psRelay4Masks 105}

r4BatteryFuse4Off OBJECT-TYPE
    SYNTAX   INTEGER{disabled(0), enabled(1)}
    MAX-ACCESS  read-write
    STATUS   current
    DESCRIPTION "Enabled(1) or Disabled (0)"
    ::= {psRelay4Masks 106}

---------------------------------------------------

r4BatteryBlockElGr1Alarm OBJECT-TYPE
    SYNTAX   INTEGER{disabled(0), enabled(1)}
    MAX-ACCESS  read-write
    STATUS   current
    DESCRIPTION "Enabled(1) or Disabled (0)"
    ::= {psRelay4Masks 111}

r4BatteryBlockElGr2Alarm OBJECT-TYPE
    SYNTAX   INTEGER{disabled(0), enabled(1)}
    MAX-ACCESS  read-write
    STATUS   current
    DESCRIPTION "Enabled(1) or Disabled (0)"
    ::= {psRelay4Masks 112}

r4BatteryBlockElGr3Alarm OBJECT-TYPE
    SYNTAX   INTEGER{disabled(0), enabled(1)}
    MAX-ACCESS  read-write
    STATUS   current
    DESCRIPTION "Enabled(1) or Disabled (0)"
    ::= {psRelay4Masks 113}

r4BatteryBlockElGr4Alarm OBJECT-TYPE
    SYNTAX   INTEGER{disabled(0), enabled(1)}
    MAX-ACCESS  read-write
    STATUS   current
    DESCRIPTION "Enabled(1) or Disabled (0)"
    ::= {psRelay4Masks 114}
----------------------------------------------------

r4UPKBAlarm OBJECT-TYPE
    SYNTAX   INTEGER{disabled(0), enabled(1)}
    MAX-ACCESS  read-write
    STATUS   current
    DESCRIPTION "Enabled(1) or Disabled (0)"
    ::= {psRelay4Masks 119}

r4ChargeCurrentLess1A OBJECT-TYPE
    SYNTAX   INTEGER{disabled(0), enabled(1)}
    MAX-ACCESS  read-write
    STATUS   current
    DESCRIPTION "Enabled(1) or Disabled (0)"
    ::= {psRelay4Masks 120}

r4ChargeCurrentLess2A OBJECT-TYPE
    SYNTAX   INTEGER{disabled(0), enabled(1)}
    MAX-ACCESS  read-write
    STATUS   current
    DESCRIPTION "Enabled(1) or Disabled (0)"
    ::= {psRelay4Masks 121}

r4ChargeCurrentLess3A OBJECT-TYPE
    SYNTAX   INTEGER{disabled(0), enabled(1)}
    MAX-ACCESS  read-write
    STATUS   current
    DESCRIPTION "Enabled(1) or Disabled (0)"
    ::= {psRelay4Masks 122}

r4ChargeCurrentLess4A OBJECT-TYPE
    SYNTAX   INTEGER{disabled(0), enabled(1)}
    MAX-ACCESS  read-write
    STATUS   current
    DESCRIPTION "Enabled(1) or Disabled (0)"
    ::= {psRelay4Masks 123}

r4ChargeCurrentLess5A OBJECT-TYPE
    SYNTAX   INTEGER{disabled(0), enabled(1)}
    MAX-ACCESS  read-write
    STATUS   current
    DESCRIPTION "Enabled(1) or Disabled (0)"
    ::= {psRelay4Masks 124}

r4BatteryOverheat OBJECT-TYPE
    SYNTAX   INTEGER{disabled(0), enabled(1)}
    MAX-ACCESS  read-write
    STATUS   current
    DESCRIPTION "Enabled(1) or Disabled (0)"
    ::= {psRelay4Masks 125}

-------------------------------------------------------------------------------------------
-------------------------------------------------------------------------------------------
r4BatteryShortTest OBJECT-TYPE
    SYNTAX   INTEGER{disabled(0), enabled(1)}
    MAX-ACCESS  read-write
    STATUS   current
    DESCRIPTION "Enabled(1) or Disabled (0)"
    ::= {psRelay4Masks 126}

r4BatteryShortTestFail OBJECT-TYPE  
    SYNTAX   INTEGER{disabled(0), enabled(1)}
    MAX-ACCESS  read-write
    STATUS   current
    DESCRIPTION "Enabled(1) or Disabled (0)"
    ::= {psRelay4Masks 127}

-------------------------------------------------------------------------------------------
-------------------------------------------------------------------------------------------

r4BLVDoff OBJECT-TYPE
    SYNTAX   INTEGER{disabled(0), enabled(1)}
    MAX-ACCESS  read-write
    STATUS   current
    DESCRIPTION "Enabled(1) or Disabled (0)"
    ::= {psRelay4Masks 128}

r4LLVD1off OBJECT-TYPE
    SYNTAX   INTEGER{disabled(0), enabled(1)}
    MAX-ACCESS  read-write
    STATUS   current
    DESCRIPTION "Enabled(1) or Disabled (0)"
    ::= {psRelay4Masks 129}

r4LLVD2off OBJECT-TYPE
    SYNTAX   INTEGER{disabled(0), enabled(1)}
    MAX-ACCESS  read-write
    STATUS   current
    DESCRIPTION "Enabled(1) or Disabled (0)"
    ::= {psRelay4Masks 130}

--VBVAlarm in psRelay4Masks
r4VBV1Alarm OBJECT-TYPE
    SYNTAX   INTEGER{disabled(0), enabled(1)}
    MAX-ACCESS  read-write
    STATUS   current
    DESCRIPTION "Alarm of rectifier1 Enabled(1) or Disabled (0)"
    ::= {psRelay4Masks 160}

r4VBV2Alarm OBJECT-TYPE
    SYNTAX   INTEGER{disabled(0), enabled(1)}
    MAX-ACCESS  read-write
    STATUS   current
    DESCRIPTION "Alarm of rectifier2 Enabled(1) or Disabled (0)"
    ::= {psRelay4Masks 161}

r4VBV3Alarm OBJECT-TYPE
    SYNTAX   INTEGER{disabled(0), enabled(1)}
    MAX-ACCESS  read-write
    STATUS   current
    DESCRIPTION "Alarm of rectifier3 Enabled(1) or Disabled (0)"
    ::= {psRelay4Masks 162}

r4VBV4Alarm OBJECT-TYPE
    SYNTAX   INTEGER{disabled(0), enabled(1)}
    MAX-ACCESS  read-write
    STATUS   current
    DESCRIPTION "Alarm of rectifier4 Enabled(1) or Disabled (0)"
    ::= {psRelay4Masks 163}

r4VBV5Alarm OBJECT-TYPE
    SYNTAX   INTEGER{disabled(0), enabled(1)}
    MAX-ACCESS  read-write
    STATUS   current
    DESCRIPTION "Alarm of rectifier5 Enabled(1) or Disabled (0)"
    ::= {psRelay4Masks 164}

r4VBV6Alarm OBJECT-TYPE
    SYNTAX   INTEGER{disabled(0), enabled(1)}
    MAX-ACCESS  read-write
    STATUS   current
    DESCRIPTION "Alarm of rectifier6 Enabled(1) or Disabled (0)"
    ::= {psRelay4Masks 165}

r4VBV7Alarm OBJECT-TYPE
    SYNTAX   INTEGER{disabled(0), enabled(1)}
    MAX-ACCESS  read-write
    STATUS   current
    DESCRIPTION "Alarm of rectifier7 Enabled(1) or Disabled (0)"
    ::= {psRelay4Masks 166}

r4VBV8Alarm OBJECT-TYPE
    SYNTAX   INTEGER{disabled(0), enabled(1)}
    MAX-ACCESS  read-write
    STATUS   current
    DESCRIPTION "Alarm of rectifier8 Enabled(1) or Disabled (0)"
    ::= {psRelay4Masks 167}

r4VBV9Alarm OBJECT-TYPE
    SYNTAX   INTEGER{disabled(0), enabled(1)}
    MAX-ACCESS  read-write
    STATUS   current
    DESCRIPTION "Alarm of rectifier9 Enabled(1) or Disabled (0)"
    ::= {psRelay4Masks 168}

r4VBV10Alarm OBJECT-TYPE
    SYNTAX   INTEGER{disabled(0), enabled(1)}
    MAX-ACCESS  read-write
    STATUS   current
    DESCRIPTION "Alarm of rectifier10 Enabled(1) or Disabled (0)"
    ::= {psRelay4Masks 169}

r4VBV11Alarm OBJECT-TYPE
    SYNTAX   INTEGER{disabled(0), enabled(1)}
    MAX-ACCESS  read-write
    STATUS   current
    DESCRIPTION "Alarm of rectifier11 Enabled(1) or Disabled (0)"
    ::= {psRelay4Masks 170}

r4VBV12Alarm OBJECT-TYPE
    SYNTAX   INTEGER{disabled(0), enabled(1)}
    MAX-ACCESS  read-write
    STATUS   current
    DESCRIPTION "Alarm of rectifier12 Enabled(1) or Disabled (0)"
    ::= {psRelay4Masks 171}

r4VBV13Alarm OBJECT-TYPE
    SYNTAX   INTEGER{disabled(0), enabled(1)}
    MAX-ACCESS  read-write
    STATUS   current
    DESCRIPTION "Alarm of rectifier13 Enabled(1) or Disabled (0)"
    ::= {psRelay4Masks 172}

r4VBV14Alarm OBJECT-TYPE
    SYNTAX   INTEGER{disabled(0), enabled(1)}
    MAX-ACCESS  read-write
    STATUS   current
    DESCRIPTION "Alarm of rectifier14 Enabled(1) or Disabled (0)"
    ::= {psRelay4Masks 173}

r4VBV15Alarm OBJECT-TYPE
    SYNTAX   INTEGER{disabled(0), enabled(1)}
    MAX-ACCESS  read-write
    STATUS   current
    DESCRIPTION "Alarm of rectifier15 Enabled(1) or Disabled (0)"
    ::= {psRelay4Masks 174}

r4VBV16Alarm OBJECT-TYPE
    SYNTAX   INTEGER{disabled(0), enabled(1)}
    MAX-ACCESS  read-write
    STATUS   current
    DESCRIPTION "Alarm of rectifier16 Enabled(1) or Disabled (0)"
    ::= {psRelay4Masks 175}

r4VBV17Alarm OBJECT-TYPE
    SYNTAX   INTEGER{disabled(0), enabled(1)}
    MAX-ACCESS  read-write
    STATUS   current
    DESCRIPTION "Alarm of rectifier17 Enabled(1) or Disabled (0)"
    ::= {psRelay4Masks 176}

r4VBV18Alarm OBJECT-TYPE
    SYNTAX   INTEGER{disabled(0), enabled(1)}
    MAX-ACCESS  read-write
    STATUS   current
    DESCRIPTION "Alarm of rectifier18 Enabled(1) or Disabled (0)"
    ::= {psRelay4Masks 177}

r4VBV19Alarm OBJECT-TYPE
    SYNTAX   INTEGER{disabled(0), enabled(1)}
    MAX-ACCESS  read-write
    STATUS   current
    DESCRIPTION "Alarm of rectifier19 Enabled(1) or Disabled (0)"
    ::= {psRelay4Masks 178}

r4VBV20Alarm OBJECT-TYPE
    SYNTAX   INTEGER{disabled(0), enabled(1)}
    MAX-ACCESS  read-write
    STATUS   current
    DESCRIPTION "Alarm of rectifier20 Enabled(1) or Disabled (0)"
    ::= {psRelay4Masks 179}

r4VBV21Alarm OBJECT-TYPE
    SYNTAX   INTEGER{disabled(0), enabled(1)}
    MAX-ACCESS  read-write
    STATUS   current
    DESCRIPTION "Alarm of rectifier21 Enabled(1) or Disabled (0)"
    ::= {psRelay4Masks 180}

r4VBV22Alarm OBJECT-TYPE
    SYNTAX   INTEGER{disabled(0), enabled(1)}
    MAX-ACCESS  read-write
    STATUS   current
    DESCRIPTION "Alarm of rectifier22 Enabled(1) or Disabled (0)"
    ::= {psRelay4Masks 181}

r4VBV23Alarm OBJECT-TYPE
    SYNTAX   INTEGER{disabled(0), enabled(1)}
    MAX-ACCESS  read-write
    STATUS   current
    DESCRIPTION "Alarm of rectifier23 Enabled(1) or Disabled (0)"
    ::= {psRelay4Masks 182}

r4VBV24Alarm OBJECT-TYPE
    SYNTAX   INTEGER{disabled(0), enabled(1)}
    MAX-ACCESS  read-write
    STATUS   current
    DESCRIPTION "Alarm of rectifier24 Enabled(1) or Disabled (0)"
    ::= {psRelay4Masks 183}

r4VBV25Alarm OBJECT-TYPE
    SYNTAX   INTEGER{disabled(0), enabled(1)}
    MAX-ACCESS  read-write
    STATUS   current
    DESCRIPTION "Alarm of rectifier25 Enabled(1) or Disabled (0)"
    ::= {psRelay4Masks 184}

r4VBV26Alarm OBJECT-TYPE
    SYNTAX   INTEGER{disabled(0), enabled(1)}
    MAX-ACCESS  read-write
    STATUS   current
    DESCRIPTION "Alarm of rectifier26 Enabled(1) or Disabled (0)"
    ::= {psRelay4Masks 185}

r4VBV27Alarm OBJECT-TYPE
    SYNTAX   INTEGER{disabled(0), enabled(1)}
    MAX-ACCESS  read-write
    STATUS   current
    DESCRIPTION "Alarm of rectifier27 Enabled(1) or Disabled (0)"
    ::= {psRelay4Masks 186}

r4VBV28Alarm OBJECT-TYPE
    SYNTAX   INTEGER{disabled(0), enabled(1)}
    MAX-ACCESS  read-write
    STATUS   current
    DESCRIPTION "Alarm of rectifier28 Enabled(1) or Disabled (0)"
    ::= {psRelay4Masks 187}

r4VBV29Alarm OBJECT-TYPE
    SYNTAX   INTEGER{disabled(0), enabled(1)}
    MAX-ACCESS  read-write
    STATUS   current
    DESCRIPTION "Alarm of rectifier29 Enabled(1) or Disabled (0)"
    ::= {psRelay4Masks 188}

r4VBV30Alarm OBJECT-TYPE
    SYNTAX   INTEGER{disabled(0), enabled(1)}
    MAX-ACCESS  read-write
    STATUS   current
    DESCRIPTION "Alarm of rectifier30 Enabled(1) or Disabled (0)"
    ::= {psRelay4Masks 189}

r4VBV31Alarm OBJECT-TYPE
    SYNTAX   INTEGER{disabled(0), enabled(1)}
    MAX-ACCESS  read-write
    STATUS   current
    DESCRIPTION "Alarm of rectifier31 Enabled(1) or Disabled (0)"
    ::= {psRelay4Masks 190}

r4VBV32Alarm OBJECT-TYPE
    SYNTAX   INTEGER{disabled(0), enabled(1)}
    MAX-ACCESS  read-write
    STATUS   current
    DESCRIPTION "Alarm of rectifier32 Enabled(1) or Disabled (0)"
    ::= {psRelay4Masks 191}

r4VBV33Alarm OBJECT-TYPE
    SYNTAX   INTEGER{disabled(0), enabled(1)}
    MAX-ACCESS  read-write
    STATUS   current
    DESCRIPTION "Alarm of rectifier33 Enabled(1) or Disabled (0)"
    ::= {psRelay4Masks 192}

r4VBV34Alarm OBJECT-TYPE
    SYNTAX   INTEGER{disabled(0), enabled(1)}
    MAX-ACCESS  read-write
    STATUS   current
    DESCRIPTION "Alarm of rectifier34 Enabled(1) or Disabled (0)"
    ::= {psRelay4Masks 193}

r4VBV35Alarm OBJECT-TYPE
    SYNTAX   INTEGER{disabled(0), enabled(1)}
    MAX-ACCESS  read-write
    STATUS   current
    DESCRIPTION "Alarm of rectifier35 Enabled(1) or Disabled (0)"
    ::= {psRelay4Masks 194}

r4VBV36Alarm OBJECT-TYPE
    SYNTAX   INTEGER{disabled(0), enabled(1)}
    MAX-ACCESS  read-write
    STATUS   current
    DESCRIPTION "Alarm of rectifier36 Enabled(1) or Disabled (0)"
    ::= {psRelay4Masks 195}

r4VBV37Alarm OBJECT-TYPE
    SYNTAX   INTEGER{disabled(0), enabled(1)}
    MAX-ACCESS  read-write
    STATUS   current
    DESCRIPTION "Alarm of rectifier37 Enabled(1) or Disabled (0)"
    ::= {psRelay4Masks 196}

r4VBV38Alarm OBJECT-TYPE
    SYNTAX   INTEGER{disabled(0), enabled(1)}
    MAX-ACCESS  read-write
    STATUS   current
    DESCRIPTION "Alarm of rectifier38 Enabled(1) or Disabled (0)"
    ::= {psRelay4Masks 197}

r4VBV39Alarm OBJECT-TYPE
    SYNTAX   INTEGER{disabled(0), enabled(1)}
    MAX-ACCESS  read-write
    STATUS   current
    DESCRIPTION "Alarm of rectifier39 Enabled(1) or Disabled (0)"
    ::= {psRelay4Masks 198}

r4VBV40Alarm OBJECT-TYPE
    SYNTAX   INTEGER{disabled(0), enabled(1)}
    MAX-ACCESS  read-write
    STATUS   current
    DESCRIPTION "Alarm of rectifier40 Enabled(1) or Disabled (0)"
    ::= {psRelay4Masks 199}

r4VBV41Alarm OBJECT-TYPE
    SYNTAX   INTEGER{disabled(0), enabled(1)}
    MAX-ACCESS  read-write
    STATUS   current
    DESCRIPTION "Alarm of rectifier41 Enabled(1) or Disabled (0)"
    ::= {psRelay4Masks 200}

r4VBV42Alarm OBJECT-TYPE
    SYNTAX   INTEGER{disabled(0), enabled(1)}
    MAX-ACCESS  read-write
    STATUS   current
    DESCRIPTION "Alarm of rectifier42 Enabled(1) or Disabled (0)"
    ::= {psRelay4Masks 201}

r4VBV43Alarm OBJECT-TYPE
    SYNTAX   INTEGER{disabled(0), enabled(1)}
    MAX-ACCESS  read-write
    STATUS   current
    DESCRIPTION "Alarm of rectifier43 Enabled(1) or Disabled (0)"
    ::= {psRelay4Masks 202}

r4VBV44Alarm OBJECT-TYPE
    SYNTAX   INTEGER{disabled(0), enabled(1)}
    MAX-ACCESS  read-write
    STATUS   current
    DESCRIPTION "Alarm of rectifier44 Enabled(1) or Disabled (0)"
    ::= {psRelay4Masks 203}

r4VBV45Alarm OBJECT-TYPE
    SYNTAX   INTEGER{disabled(0), enabled(1)}
    MAX-ACCESS  read-write
    STATUS   current
    DESCRIPTION "Alarm of rectifier45 Enabled(1) or Disabled (0)"
    ::= {psRelay4Masks 204}

r4VBV46Alarm OBJECT-TYPE
    SYNTAX   INTEGER{disabled(0), enabled(1)}
    MAX-ACCESS  read-write
    STATUS   current
    DESCRIPTION "Alarm of rectifier46 Enabled(1) or Disabled (0)"
    ::= {psRelay4Masks 205}

r4VBV47Alarm OBJECT-TYPE
    SYNTAX   INTEGER{disabled(0), enabled(1)}
    MAX-ACCESS  read-write
    STATUS   current
    DESCRIPTION "Alarm of rectifier47 Enabled(1) or Disabled (0)"
    ::= {psRelay4Masks 206}

r4VBV48Alarm OBJECT-TYPE
    SYNTAX   INTEGER{disabled(0), enabled(1)}
    MAX-ACCESS  read-write
    STATUS   current
    DESCRIPTION "Alarm of rectifier48 Enabled(1) or Disabled (0)"
    ::= {psRelay4Masks 207}

r4VBV49Alarm OBJECT-TYPE
    SYNTAX   INTEGER{disabled(0), enabled(1)}
    MAX-ACCESS  read-write
    STATUS   current
    DESCRIPTION "Alarm of rectifier49 Enabled(1) or Disabled (0)"
    ::= {psRelay4Masks 208}

r4VBV50Alarm OBJECT-TYPE
    SYNTAX   INTEGER{disabled(0), enabled(1)}
    MAX-ACCESS  read-write
    STATUS   current
    DESCRIPTION "Alarm of rectifier50 Enabled(1) or Disabled (0)"
    ::= {psRelay4Masks 209}

r4VBV51Alarm OBJECT-TYPE
    SYNTAX   INTEGER{disabled(0), enabled(1)}
    MAX-ACCESS  read-write
    STATUS   current
    DESCRIPTION "Alarm of rectifier51 Enabled(1) or Disabled (0)"
    ::= {psRelay4Masks 210}

r4VBV52Alarm OBJECT-TYPE
    SYNTAX   INTEGER{disabled(0), enabled(1)}
    MAX-ACCESS  read-write
    STATUS   current
    DESCRIPTION "Alarm of rectifier52 Enabled(1) or Disabled (0)"
    ::= {psRelay4Masks 211}

r4VBV53Alarm OBJECT-TYPE
    SYNTAX   INTEGER{disabled(0), enabled(1)}
    MAX-ACCESS  read-write
    STATUS   current
    DESCRIPTION "Alarm of rectifier53 Enabled(1) or Disabled (0)"
    ::= {psRelay4Masks 212}

r4VBV54Alarm OBJECT-TYPE
    SYNTAX   INTEGER{disabled(0), enabled(1)}
    MAX-ACCESS  read-write
    STATUS   current
    DESCRIPTION "Alarm of rectifier54 Enabled(1) or Disabled (0)"
    ::= {psRelay4Masks 213}

r4VBV55Alarm OBJECT-TYPE
    SYNTAX   INTEGER{disabled(0), enabled(1)}
    MAX-ACCESS  read-write
    STATUS   current
    DESCRIPTION "Alarm of rectifier55 Enabled(1) or Disabled (0)"
    ::= {psRelay4Masks 214}

r4VBV56Alarm OBJECT-TYPE
    SYNTAX   INTEGER{disabled(0), enabled(1)}
    MAX-ACCESS  read-write
    STATUS   current
    DESCRIPTION "Alarm of rectifier56 Enabled(1) or Disabled (0)"
    ::= {psRelay4Masks 215}

r4VBV57Alarm OBJECT-TYPE
    SYNTAX   INTEGER{disabled(0), enabled(1)}
    MAX-ACCESS  read-write
    STATUS   current
    DESCRIPTION "Alarm of rectifier57 Enabled(1) or Disabled (0)"
    ::= {psRelay4Masks 216}

r4VBV58Alarm OBJECT-TYPE
    SYNTAX   INTEGER{disabled(0), enabled(1)}
    MAX-ACCESS  read-write
    STATUS   current
    DESCRIPTION "Alarm of rectifier58 Enabled(1) or Disabled (0)"
    ::= {psRelay4Masks 217}

r4VBV59Alarm OBJECT-TYPE
    SYNTAX   INTEGER{disabled(0), enabled(1)}
    MAX-ACCESS  read-write
    STATUS   current
    DESCRIPTION "Alarm of rectifier59 Enabled(1) or Disabled (0)"
    ::= {psRelay4Masks 218}

r4VBV60Alarm OBJECT-TYPE
    SYNTAX   INTEGER{disabled(0), enabled(1)}
    MAX-ACCESS  read-write
    STATUS   current
    DESCRIPTION "Alarm of rectifier60 Enabled(1) or Disabled (0)"
    ::= {psRelay4Masks 219}

r4VBV61Alarm OBJECT-TYPE
    SYNTAX   INTEGER{disabled(0), enabled(1)}
    MAX-ACCESS  read-write
    STATUS   current
    DESCRIPTION "Alarm of rectifier61 Enabled(1) or Disabled (0)"
    ::= {psRelay4Masks 220}

r4VBV62Alarm OBJECT-TYPE
    SYNTAX   INTEGER{disabled(0), enabled(1)}
    MAX-ACCESS  read-write
    STATUS   current
    DESCRIPTION "Alarm of rectifier62 Enabled(1) or Disabled (0)"
    ::= {psRelay4Masks 221}

r4VBV63Alarm OBJECT-TYPE
    SYNTAX   INTEGER{disabled(0), enabled(1)}
    MAX-ACCESS  read-write
    STATUS   current
    DESCRIPTION "Alarm of rectifier63 Enabled(1) or Disabled (0)"
    ::= {psRelay4Masks 222}

r4VBV64Alarm OBJECT-TYPE
    SYNTAX   INTEGER{disabled(0), enabled(1)}
    MAX-ACCESS  read-write
    STATUS   current
    DESCRIPTION "Alarm of rectifier64 Enabled(1) or Disabled (0)"
    ::= {psRelay4Masks 223}

r4VBV65Alarm OBJECT-TYPE
    SYNTAX   INTEGER{disabled(0), enabled(1)}
    MAX-ACCESS  read-write
    STATUS   current
    DESCRIPTION "Alarm of rectifier65 Enabled(1) or Disabled (0)"
    ::= {psRelay4Masks 224}

r4VBV66Alarm OBJECT-TYPE
    SYNTAX   INTEGER{disabled(0), enabled(1)}
    MAX-ACCESS  read-write
    STATUS   current
    DESCRIPTION "Alarm of rectifier66 Enabled(1) or Disabled (0)"
    ::= {psRelay4Masks 225}

r4VBV67Alarm OBJECT-TYPE
    SYNTAX   INTEGER{disabled(0), enabled(1)}
    MAX-ACCESS  read-write
    STATUS   current
    DESCRIPTION "Alarm of rectifier67 Enabled(1) or Disabled (0)"
    ::= {psRelay4Masks 226}

r4VBV68Alarm OBJECT-TYPE
    SYNTAX   INTEGER{disabled(0), enabled(1)}
    MAX-ACCESS  read-write
    STATUS   current
    DESCRIPTION "Alarm of rectifier68 Enabled(1) or Disabled (0)"
    ::= {psRelay4Masks 227}

r4VBV69Alarm OBJECT-TYPE
    SYNTAX   INTEGER{disabled(0), enabled(1)}
    MAX-ACCESS  read-write
    STATUS   current
    DESCRIPTION "Alarm of rectifier69 Enabled(1) or Disabled (0)"
    ::= {psRelay4Masks 228}

r4VBV70Alarm OBJECT-TYPE
    SYNTAX   INTEGER{disabled(0), enabled(1)}
    MAX-ACCESS  read-write
    STATUS   current
    DESCRIPTION "Alarm of rectifier70 Enabled(1) or Disabled (0)"
    ::= {psRelay4Masks 229}

r4VBV71Alarm OBJECT-TYPE
    SYNTAX   INTEGER{disabled(0), enabled(1)}
    MAX-ACCESS  read-write
    STATUS   current
    DESCRIPTION "Alarm of rectifier71 Enabled(1) or Disabled (0)"
    ::= {psRelay4Masks 230}

r4VBV72Alarm OBJECT-TYPE
    SYNTAX   INTEGER{disabled(0), enabled(1)}
    MAX-ACCESS  read-write
    STATUS   current
    DESCRIPTION "Alarm of rectifier72 Enabled(1) or Disabled (0)"
    ::= {psRelay4Masks 231}

r4VBV73Alarm OBJECT-TYPE
    SYNTAX   INTEGER{disabled(0), enabled(1)}
    MAX-ACCESS  read-write
    STATUS   current
    DESCRIPTION "Alarm of rectifier73 Enabled(1) or Disabled (0)"
    ::= {psRelay4Masks 232}

r4VBV74Alarm OBJECT-TYPE
    SYNTAX   INTEGER{disabled(0), enabled(1)}
    MAX-ACCESS  read-write
    STATUS   current
    DESCRIPTION "Alarm of rectifier74 Enabled(1) or Disabled (0)"
    ::= {psRelay4Masks 233}

r4VBV75Alarm OBJECT-TYPE
    SYNTAX   INTEGER{disabled(0), enabled(1)}
    MAX-ACCESS  read-write
    STATUS   current
    DESCRIPTION "Alarm of rectifier75 Enabled(1) or Disabled (0)"
    ::= {psRelay4Masks 234}

r4VBV76Alarm OBJECT-TYPE
    SYNTAX   INTEGER{disabled(0), enabled(1)}
    MAX-ACCESS  read-write
    STATUS   current
    DESCRIPTION "Alarm of rectifier76 Enabled(1) or Disabled (0)"
    ::= {psRelay4Masks 235}

r4VBV77Alarm OBJECT-TYPE
    SYNTAX   INTEGER{disabled(0), enabled(1)}
    MAX-ACCESS  read-write
    STATUS   current
    DESCRIPTION "Alarm of rectifier77 Enabled(1) or Disabled (0)"
    ::= {psRelay4Masks 236}

r4VBV78Alarm OBJECT-TYPE
    SYNTAX   INTEGER{disabled(0), enabled(1)}
    MAX-ACCESS  read-write
    STATUS   current
    DESCRIPTION "Alarm of rectifier78 Enabled(1) or Disabled (0)"
    ::= {psRelay4Masks 237}

r4VBV79Alarm OBJECT-TYPE
    SYNTAX   INTEGER{disabled(0), enabled(1)}
    MAX-ACCESS  read-write
    STATUS   current
    DESCRIPTION "Alarm of rectifier79 Enabled(1) or Disabled (0)"
    ::= {psRelay4Masks 238}

r4VBV80Alarm OBJECT-TYPE
    SYNTAX   INTEGER{disabled(0), enabled(1)}
    MAX-ACCESS  read-write
    STATUS   current
    DESCRIPTION "Alarm of rectifier80 Enabled(1) or Disabled (0)"
    ::= {psRelay4Masks 239}

r4VBV81Alarm OBJECT-TYPE
    SYNTAX   INTEGER{disabled(0), enabled(1)}
    MAX-ACCESS  read-write
    STATUS   current
    DESCRIPTION "Alarm of rectifier81 Enabled(1) or Disabled (0)"
    ::= {psRelay4Masks 240}

r4VBV82Alarm OBJECT-TYPE
    SYNTAX   INTEGER{disabled(0), enabled(1)}
    MAX-ACCESS  read-write
    STATUS   current
    DESCRIPTION "Alarm of rectifier82 Enabled(1) or Disabled (0)"
    ::= {psRelay4Masks 241}

r4VBV83Alarm OBJECT-TYPE
    SYNTAX   INTEGER{disabled(0), enabled(1)}
    MAX-ACCESS  read-write
    STATUS   current
    DESCRIPTION "Alarm of rectifier83 Enabled(1) or Disabled (0)"
    ::= {psRelay4Masks 242}

r4VBV84Alarm OBJECT-TYPE
    SYNTAX   INTEGER{disabled(0), enabled(1)}
    MAX-ACCESS  read-write
    STATUS   current
    DESCRIPTION "Alarm of rectifier84 Enabled(1) or Disabled (0)"
    ::= {psRelay4Masks 243}

r4VBV85Alarm OBJECT-TYPE
    SYNTAX   INTEGER{disabled(0), enabled(1)}
    MAX-ACCESS  read-write
    STATUS   current
    DESCRIPTION "Alarm of rectifier85 Enabled(1) or Disabled (0)"
    ::= {psRelay4Masks 244}

r4VBV86Alarm OBJECT-TYPE
    SYNTAX   INTEGER{disabled(0), enabled(1)}
    MAX-ACCESS  read-write
    STATUS   current
    DESCRIPTION "Alarm of rectifier86 Enabled(1) or Disabled (0)"
    ::= {psRelay4Masks 245}

r4VBV87Alarm OBJECT-TYPE
    SYNTAX   INTEGER{disabled(0), enabled(1)}
    MAX-ACCESS  read-write
    STATUS   current
    DESCRIPTION "Alarm of rectifier87 Enabled(1) or Disabled (0)"
    ::= {psRelay4Masks 246}

r4VBV88Alarm OBJECT-TYPE
    SYNTAX   INTEGER{disabled(0), enabled(1)}
    MAX-ACCESS  read-write
    STATUS   current
    DESCRIPTION "Alarm of rectifier88 Enabled(1) or Disabled (0)"
    ::= {psRelay4Masks 247}

r4VBV89Alarm OBJECT-TYPE
    SYNTAX   INTEGER{disabled(0), enabled(1)}
    MAX-ACCESS  read-write
    STATUS   current
    DESCRIPTION "Alarm of rectifier89 Enabled(1) or Disabled (0)"
    ::= {psRelay4Masks 248}

r4VBV90Alarm OBJECT-TYPE
    SYNTAX   INTEGER{disabled(0), enabled(1)}
    MAX-ACCESS  read-write
    STATUS   current
    DESCRIPTION "Alarm of rectifier90 Enabled(1) or Disabled (0)"
    ::= {psRelay4Masks 249}

r4VBV91Alarm OBJECT-TYPE
    SYNTAX   INTEGER{disabled(0), enabled(1)}
    MAX-ACCESS  read-write
    STATUS   current
    DESCRIPTION "Alarm of rectifier91 Enabled(1) or Disabled (0)"
    ::= {psRelay4Masks 250}

r4VBV92Alarm OBJECT-TYPE
    SYNTAX   INTEGER{disabled(0), enabled(1)}
    MAX-ACCESS  read-write
    STATUS   current
    DESCRIPTION "Alarm of rectifier92 Enabled(1) or Disabled (0)"
    ::= {psRelay4Masks 251}

r4VBV93Alarm OBJECT-TYPE
    SYNTAX   INTEGER{disabled(0), enabled(1)}
    MAX-ACCESS  read-write
    STATUS   current
    DESCRIPTION "Alarm of rectifier93 Enabled(1) or Disabled (0)"
    ::= {psRelay4Masks 252}

r4VBV94Alarm OBJECT-TYPE
    SYNTAX   INTEGER{disabled(0), enabled(1)}
    MAX-ACCESS  read-write
    STATUS   current
    DESCRIPTION "Alarm of rectifier94 Enabled(1) or Disabled (0)"
    ::= {psRelay4Masks 253}

r4VBV95Alarm OBJECT-TYPE
    SYNTAX   INTEGER{disabled(0), enabled(1)}
    MAX-ACCESS  read-write
    STATUS   current
    DESCRIPTION "Alarm of rectifier95 Enabled(1) or Disabled (0)"
    ::= {psRelay4Masks 254}

r4VBV96Alarm OBJECT-TYPE
    SYNTAX   INTEGER{disabled(0), enabled(1)}
    MAX-ACCESS  read-write
    STATUS   current
    DESCRIPTION "Alarm of rectifier96 Enabled(1) or Disabled (0)"
    ::= {psRelay4Masks 255}

r4VBV97Alarm OBJECT-TYPE
    SYNTAX   INTEGER{disabled(0), enabled(1)}
    MAX-ACCESS  read-write
    STATUS   current
    DESCRIPTION "Alarm of rectifier97 Enabled(1) or Disabled (0)"
    ::= {psRelay4Masks 256}

r4VBV98Alarm OBJECT-TYPE
    SYNTAX   INTEGER{disabled(0), enabled(1)}
    MAX-ACCESS  read-write
    STATUS   current
    DESCRIPTION "Alarm of rectifier98 Enabled(1) or Disabled (0)"
    ::= {psRelay4Masks 257}

r4VBV99Alarm OBJECT-TYPE
    SYNTAX   INTEGER{disabled(0), enabled(1)}
    MAX-ACCESS  read-write
    STATUS   current
    DESCRIPTION "Alarm of rectifier99 Enabled(1) or Disabled (0)"
    ::= {psRelay4Masks 258}

r4VBV100Alarm OBJECT-TYPE
    SYNTAX   INTEGER{disabled(0), enabled(1)}
    MAX-ACCESS  read-write
    STATUS   current
    DESCRIPTION "Alarm of rectifier100 Enabled(1) or Disabled (0)"
    ::= {psRelay4Masks 259}

r4VBV101Alarm OBJECT-TYPE
    SYNTAX   INTEGER{disabled(0), enabled(1)}
    MAX-ACCESS  read-write
    STATUS   current
    DESCRIPTION "Alarm of rectifier101 Enabled(1) or Disabled (0)"
    ::= {psRelay4Masks 260}

r4VBV102Alarm OBJECT-TYPE
    SYNTAX   INTEGER{disabled(0), enabled(1)}
    MAX-ACCESS  read-write
    STATUS   current
    DESCRIPTION "Alarm of rectifier102 Enabled(1) or Disabled (0)"
    ::= {psRelay4Masks 261}

r4VBV103Alarm OBJECT-TYPE
    SYNTAX   INTEGER{disabled(0), enabled(1)}
    MAX-ACCESS  read-write
    STATUS   current
    DESCRIPTION "Alarm of rectifier103 Enabled(1) or Disabled (0)"
    ::= {psRelay4Masks 262}

r4VBV104Alarm OBJECT-TYPE
    SYNTAX   INTEGER{disabled(0), enabled(1)}
    MAX-ACCESS  read-write
    STATUS   current
    DESCRIPTION "Alarm of rectifier104 Enabled(1) or Disabled (0)"
    ::= {psRelay4Masks 263}

r4VBV105Alarm OBJECT-TYPE
    SYNTAX   INTEGER{disabled(0), enabled(1)}
    MAX-ACCESS  read-write
    STATUS   current
    DESCRIPTION "Alarm of rectifier105 Enabled(1) or Disabled (0)"
    ::= {psRelay4Masks 264}

r4VBV106Alarm OBJECT-TYPE
    SYNTAX   INTEGER{disabled(0), enabled(1)}
    MAX-ACCESS  read-write
    STATUS   current
    DESCRIPTION "Alarm of rectifier106 Enabled(1) or Disabled (0)"
    ::= {psRelay4Masks 265}

r4VBV107Alarm OBJECT-TYPE
    SYNTAX   INTEGER{disabled(0), enabled(1)}
    MAX-ACCESS  read-write
    STATUS   current
    DESCRIPTION "Alarm of rectifier107 Enabled(1) or Disabled (0)"
    ::= {psRelay4Masks 266}

r4VBV108Alarm OBJECT-TYPE
    SYNTAX   INTEGER{disabled(0), enabled(1)}
    MAX-ACCESS  read-write
    STATUS   current
    DESCRIPTION "Alarm of rectifier108 Enabled(1) or Disabled (0)"
    ::= {psRelay4Masks 267}

r4VBV109Alarm OBJECT-TYPE
    SYNTAX   INTEGER{disabled(0), enabled(1)}
    MAX-ACCESS  read-write
    STATUS   current
    DESCRIPTION "Alarm of rectifier109 Enabled(1) or Disabled (0)"
    ::= {psRelay4Masks 268}

r4VBV110Alarm OBJECT-TYPE
    SYNTAX   INTEGER{disabled(0), enabled(1)}
    MAX-ACCESS  read-write
    STATUS   current
    DESCRIPTION "Alarm of rectifier110 Enabled(1) or Disabled (0)"
    ::= {psRelay4Masks 269}

r4VBV111Alarm OBJECT-TYPE
    SYNTAX   INTEGER{disabled(0), enabled(1)}
    MAX-ACCESS  read-write
    STATUS   current
    DESCRIPTION "Alarm of rectifier111 Enabled(1) or Disabled (0)"
    ::= {psRelay4Masks 270}

r4VBV112Alarm OBJECT-TYPE
    SYNTAX   INTEGER{disabled(0), enabled(1)}
    MAX-ACCESS  read-write
    STATUS   current
    DESCRIPTION "Alarm of rectifier112 Enabled(1) or Disabled (0)"
    ::= {psRelay4Masks 271}

r4VBV113Alarm OBJECT-TYPE
    SYNTAX   INTEGER{disabled(0), enabled(1)}
    MAX-ACCESS  read-write
    STATUS   current
    DESCRIPTION "Alarm of rectifier113 Enabled(1) or Disabled (0)"
    ::= {psRelay4Masks 272}

r4VBV114Alarm OBJECT-TYPE
    SYNTAX   INTEGER{disabled(0), enabled(1)}
    MAX-ACCESS  read-write
    STATUS   current
    DESCRIPTION "Alarm of rectifier114 Enabled(1) or Disabled (0)"
    ::= {psRelay4Masks 273}

r4VBV115Alarm OBJECT-TYPE
    SYNTAX   INTEGER{disabled(0), enabled(1)}
    MAX-ACCESS  read-write
    STATUS   current
    DESCRIPTION "Alarm of rectifier115 Enabled(1) or Disabled (0)"
    ::= {psRelay4Masks 274}

r4VBV116Alarm OBJECT-TYPE
    SYNTAX   INTEGER{disabled(0), enabled(1)}
    MAX-ACCESS  read-write
    STATUS   current
    DESCRIPTION "Alarm of rectifier116 Enabled(1) or Disabled (0)"
    ::= {psRelay4Masks 275}

r4VBV117Alarm OBJECT-TYPE
    SYNTAX   INTEGER{disabled(0), enabled(1)}
    MAX-ACCESS  read-write
    STATUS   current
    DESCRIPTION "Alarm of rectifier117 Enabled(1) or Disabled (0)"
    ::= {psRelay4Masks 276}

r4VBV118Alarm OBJECT-TYPE
    SYNTAX   INTEGER{disabled(0), enabled(1)}
    MAX-ACCESS  read-write
    STATUS   current
    DESCRIPTION "Alarm of rectifier118 Enabled(1) or Disabled (0)"
    ::= {psRelay4Masks 277}

r4VBV119Alarm OBJECT-TYPE
    SYNTAX   INTEGER{disabled(0), enabled(1)}
    MAX-ACCESS  read-write
    STATUS   current
    DESCRIPTION "Alarm of rectifier119 Enabled(1) or Disabled (0)"
    ::= {psRelay4Masks 278}

r4VBV120Alarm OBJECT-TYPE
    SYNTAX   INTEGER{disabled(0), enabled(1)}
    MAX-ACCESS  read-write
    STATUS   current
    DESCRIPTION "Alarm of rectifier120 Enabled(1) or Disabled (0)"
    ::= {psRelay4Masks 279}

r4VBV121Alarm OBJECT-TYPE
    SYNTAX   INTEGER{disabled(0), enabled(1)}
    MAX-ACCESS  read-write
    STATUS   current
    DESCRIPTION "Alarm of rectifier121 Enabled(1) or Disabled (0)"
    ::= {psRelay4Masks 280}

r4VBV122Alarm OBJECT-TYPE
    SYNTAX   INTEGER{disabled(0), enabled(1)}
    MAX-ACCESS  read-write
    STATUS   current
    DESCRIPTION "Alarm of rectifier122 Enabled(1) or Disabled (0)"
    ::= {psRelay4Masks 281}

r4VBV123Alarm OBJECT-TYPE
    SYNTAX   INTEGER{disabled(0), enabled(1)}
    MAX-ACCESS  read-write
    STATUS   current
    DESCRIPTION "Alarm of rectifier123 Enabled(1) or Disabled (0)"
    ::= {psRelay4Masks 282}

r4VBV124Alarm OBJECT-TYPE
    SYNTAX   INTEGER{disabled(0), enabled(1)}
    MAX-ACCESS  read-write
    STATUS   current
    DESCRIPTION "Alarm of rectifier124 Enabled(1) or Disabled (0)"
    ::= {psRelay4Masks 283}

r4VBV125Alarm OBJECT-TYPE
    SYNTAX   INTEGER{disabled(0), enabled(1)}
    MAX-ACCESS  read-write
    STATUS   current
    DESCRIPTION "Alarm of rectifier125 Enabled(1) or Disabled (0)"
    ::= {psRelay4Masks 284}

r4VBV126Alarm OBJECT-TYPE
    SYNTAX   INTEGER{disabled(0), enabled(1)}
    MAX-ACCESS  read-write
    STATUS   current
    DESCRIPTION "Alarm of rectifier126 Enabled(1) or Disabled (0)"
    ::= {psRelay4Masks 285}

r4VBV127Alarm OBJECT-TYPE
    SYNTAX   INTEGER{disabled(0), enabled(1)}
    MAX-ACCESS  read-write
    STATUS   current
    DESCRIPTION "Alarm of rectifier127 Enabled(1) or Disabled (0)"
    ::= {psRelay4Masks 286}

r4VBV128Alarm OBJECT-TYPE
    SYNTAX   INTEGER{disabled(0), enabled(1)}
    MAX-ACCESS  read-write
    STATUS   current
    DESCRIPTION "Alarm of rectifier128 Enabled(1) or Disabled (0)"
    ::= {psRelay4Masks 287}

r4VBV129Alarm OBJECT-TYPE
    SYNTAX   INTEGER{disabled(0), enabled(1)}
    MAX-ACCESS  read-write
    STATUS   current
    DESCRIPTION "Alarm of rectifier129 Enabled(1) or Disabled (0)"
    ::= {psRelay4Masks 288}

r4VBV130Alarm OBJECT-TYPE
    SYNTAX   INTEGER{disabled(0), enabled(1)}
    MAX-ACCESS  read-write
    STATUS   current
    DESCRIPTION "Alarm of rectifier130 Enabled(1) or Disabled (0)"
    ::= {psRelay4Masks 289}

r4VBV131Alarm OBJECT-TYPE
    SYNTAX   INTEGER{disabled(0), enabled(1)}
    MAX-ACCESS  read-write
    STATUS   current
    DESCRIPTION "Alarm of rectifier131 Enabled(1) or Disabled (0)"
    ::= {psRelay4Masks 290}

r4VBV132Alarm OBJECT-TYPE
    SYNTAX   INTEGER{disabled(0), enabled(1)}
    MAX-ACCESS  read-write
    STATUS   current
    DESCRIPTION "Alarm of rectifier132 Enabled(1) or Disabled (0)"
    ::= {psRelay4Masks 291}

r4VBV133Alarm OBJECT-TYPE
    SYNTAX   INTEGER{disabled(0), enabled(1)}
    MAX-ACCESS  read-write
    STATUS   current
    DESCRIPTION "Alarm of rectifier133 Enabled(1) or Disabled (0)"
    ::= {psRelay4Masks 292}

r4VBV134Alarm OBJECT-TYPE
    SYNTAX   INTEGER{disabled(0), enabled(1)}
    MAX-ACCESS  read-write
    STATUS   current
    DESCRIPTION "Alarm of rectifier134 Enabled(1) or Disabled (0)"
    ::= {psRelay4Masks 293}

r4VBV135Alarm OBJECT-TYPE
    SYNTAX   INTEGER{disabled(0), enabled(1)}
    MAX-ACCESS  read-write
    STATUS   current
    DESCRIPTION "Alarm of rectifier135 Enabled(1) or Disabled (0)"
    ::= {psRelay4Masks 294}

r4VBV136Alarm OBJECT-TYPE
    SYNTAX   INTEGER{disabled(0), enabled(1)}
    MAX-ACCESS  read-write
    STATUS   current
    DESCRIPTION "Alarm of rectifier136 Enabled(1) or Disabled (0)"
    ::= {psRelay4Masks 295}

r4VBV137Alarm OBJECT-TYPE
    SYNTAX   INTEGER{disabled(0), enabled(1)}
    MAX-ACCESS  read-write
    STATUS   current
    DESCRIPTION "Alarm of rectifier137 Enabled(1) or Disabled (0)"
    ::= {psRelay4Masks 296}

r4VBV138Alarm OBJECT-TYPE
    SYNTAX   INTEGER{disabled(0), enabled(1)}
    MAX-ACCESS  read-write
    STATUS   current
    DESCRIPTION "Alarm of rectifier138 Enabled(1) or Disabled (0)"
    ::= {psRelay4Masks 297}

r4VBV139Alarm OBJECT-TYPE
    SYNTAX   INTEGER{disabled(0), enabled(1)}
    MAX-ACCESS  read-write
    STATUS   current
    DESCRIPTION "Alarm of rectifier139 Enabled(1) or Disabled (0)"
    ::= {psRelay4Masks 298}

r4VBV140Alarm OBJECT-TYPE
    SYNTAX   INTEGER{disabled(0), enabled(1)}
    MAX-ACCESS  read-write
    STATUS   current
    DESCRIPTION "Alarm of rectifier140 Enabled(1) or Disabled (0)"
    ::= {psRelay4Masks 299}

r4VBV141Alarm OBJECT-TYPE
    SYNTAX   INTEGER{disabled(0), enabled(1)}
    MAX-ACCESS  read-write
    STATUS   current
    DESCRIPTION "Alarm of rectifier141 Enabled(1) or Disabled (0)"
    ::= {psRelay4Masks 300}

r4VBV142Alarm OBJECT-TYPE
    SYNTAX   INTEGER{disabled(0), enabled(1)}
    MAX-ACCESS  read-write
    STATUS   current
    DESCRIPTION "Alarm of rectifier142 Enabled(1) or Disabled (0)"
    ::= {psRelay4Masks 301}

r4VBV143Alarm OBJECT-TYPE
    SYNTAX   INTEGER{disabled(0), enabled(1)}
    MAX-ACCESS  read-write
    STATUS   current
    DESCRIPTION "Alarm of rectifier143 Enabled(1) or Disabled (0)"
    ::= {psRelay4Masks 302}

r4VBV144Alarm OBJECT-TYPE
    SYNTAX   INTEGER{disabled(0), enabled(1)}
    MAX-ACCESS  read-write
    STATUS   current
    DESCRIPTION "Alarm of rectifier144 Enabled(1) or Disabled (0)"
    ::= {psRelay4Masks 303}

r4VBV145Alarm OBJECT-TYPE
    SYNTAX   INTEGER{disabled(0), enabled(1)}
    MAX-ACCESS  read-write
    STATUS   current
    DESCRIPTION "Alarm of rectifier145 Enabled(1) or Disabled (0)"
    ::= {psRelay4Masks 304}

r4VBV146Alarm OBJECT-TYPE
    SYNTAX   INTEGER{disabled(0), enabled(1)}
    MAX-ACCESS  read-write
    STATUS   current
    DESCRIPTION "Alarm of rectifier146 Enabled(1) or Disabled (0)"
    ::= {psRelay4Masks 305}

r4VBV147Alarm OBJECT-TYPE
    SYNTAX   INTEGER{disabled(0), enabled(1)}
    MAX-ACCESS  read-write
    STATUS   current
    DESCRIPTION "Alarm of rectifier147 Enabled(1) or Disabled (0)"
    ::= {psRelay4Masks 306}

r4VBV148Alarm OBJECT-TYPE
    SYNTAX   INTEGER{disabled(0), enabled(1)}
    MAX-ACCESS  read-write
    STATUS   current
    DESCRIPTION "Alarm of rectifier148 Enabled(1) or Disabled (0)"
    ::= {psRelay4Masks 307}

r4VBV149Alarm OBJECT-TYPE
    SYNTAX   INTEGER{disabled(0), enabled(1)}
    MAX-ACCESS  read-write
    STATUS   current
    DESCRIPTION "Alarm of rectifier149 Enabled(1) or Disabled (0)"
    ::= {psRelay4Masks 308}

r4VBV150Alarm OBJECT-TYPE
    SYNTAX   INTEGER{disabled(0), enabled(1)}
    MAX-ACCESS  read-write
    STATUS   current
    DESCRIPTION "Alarm of rectifier150 Enabled(1) or Disabled (0)"
    ::= {psRelay4Masks 309}

r4VBV151Alarm OBJECT-TYPE
    SYNTAX   INTEGER{disabled(0), enabled(1)}
    MAX-ACCESS  read-write
    STATUS   current
    DESCRIPTION "Alarm of rectifier151 Enabled(1) or Disabled (0)"
    ::= {psRelay4Masks 310}

r4VBV152Alarm OBJECT-TYPE
    SYNTAX   INTEGER{disabled(0), enabled(1)}
    MAX-ACCESS  read-write
    STATUS   current
    DESCRIPTION "Alarm of rectifier152 Enabled(1) or Disabled (0)"
    ::= {psRelay4Masks 311}

r4VBV153Alarm OBJECT-TYPE
    SYNTAX   INTEGER{disabled(0), enabled(1)}
    MAX-ACCESS  read-write
    STATUS   current
    DESCRIPTION "Alarm of rectifier153 Enabled(1) or Disabled (0)"
    ::= {psRelay4Masks 312}

r4VBV154Alarm OBJECT-TYPE
    SYNTAX   INTEGER{disabled(0), enabled(1)}
    MAX-ACCESS  read-write
    STATUS   current
    DESCRIPTION "Alarm of rectifier154 Enabled(1) or Disabled (0)"
    ::= {psRelay4Masks 313}

r4VBV155Alarm OBJECT-TYPE
    SYNTAX   INTEGER{disabled(0), enabled(1)}
    MAX-ACCESS  read-write
    STATUS   current
    DESCRIPTION "Alarm of rectifier155 Enabled(1) or Disabled (0)"
    ::= {psRelay4Masks 314}

r4VBV156Alarm OBJECT-TYPE
    SYNTAX   INTEGER{disabled(0), enabled(1)}
    MAX-ACCESS  read-write
    STATUS   current
    DESCRIPTION "Alarm of rectifier156 Enabled(1) or Disabled (0)"
    ::= {psRelay4Masks 315}

r4VBV157Alarm OBJECT-TYPE
    SYNTAX   INTEGER{disabled(0), enabled(1)}
    MAX-ACCESS  read-write
    STATUS   current
    DESCRIPTION "Alarm of rectifier157 Enabled(1) or Disabled (0)"
    ::= {psRelay4Masks 316}

r4VBV158Alarm OBJECT-TYPE
    SYNTAX   INTEGER{disabled(0), enabled(1)}
    MAX-ACCESS  read-write
    STATUS   current
    DESCRIPTION "Alarm of rectifier158 Enabled(1) or Disabled (0)"
    ::= {psRelay4Masks 317}

r4VBV159Alarm OBJECT-TYPE
    SYNTAX   INTEGER{disabled(0), enabled(1)}
    MAX-ACCESS  read-write
    STATUS   current
    DESCRIPTION "Alarm of rectifier159 Enabled(1) or Disabled (0)"
    ::= {psRelay4Masks 318}

r4VBV160Alarm OBJECT-TYPE
    SYNTAX   INTEGER{disabled(0), enabled(1)}
    MAX-ACCESS  read-write
    STATUS   current
    DESCRIPTION "Alarm of rectifier160 Enabled(1) or Disabled (0)"
    ::= {psRelay4Masks 319}

r4VBV161Alarm OBJECT-TYPE
    SYNTAX   INTEGER{disabled(0), enabled(1)}
    MAX-ACCESS  read-write
    STATUS   current
    DESCRIPTION "Alarm of rectifier161 Enabled(1) or Disabled (0)"
    ::= {psRelay4Masks 320}

r4VBV162Alarm OBJECT-TYPE
    SYNTAX   INTEGER{disabled(0), enabled(1)}
    MAX-ACCESS  read-write
    STATUS   current
    DESCRIPTION "Alarm of rectifier162 Enabled(1) or Disabled (0)"
    ::= {psRelay4Masks 321}

r4VBV163Alarm OBJECT-TYPE
    SYNTAX   INTEGER{disabled(0), enabled(1)}
    MAX-ACCESS  read-write
    STATUS   current
    DESCRIPTION "Alarm of rectifier163 Enabled(1) or Disabled (0)"
    ::= {psRelay4Masks 322}

r4VBV164Alarm OBJECT-TYPE
    SYNTAX   INTEGER{disabled(0), enabled(1)}
    MAX-ACCESS  read-write
    STATUS   current
    DESCRIPTION "Alarm of rectifier164 Enabled(1) or Disabled (0)"
    ::= {psRelay4Masks 323}

r4VBV165Alarm OBJECT-TYPE
    SYNTAX   INTEGER{disabled(0), enabled(1)}
    MAX-ACCESS  read-write
    STATUS   current
    DESCRIPTION "Alarm of rectifier165 Enabled(1) or Disabled (0)"
    ::= {psRelay4Masks 324}

r4VBV166Alarm OBJECT-TYPE
    SYNTAX   INTEGER{disabled(0), enabled(1)}
    MAX-ACCESS  read-write
    STATUS   current
    DESCRIPTION "Alarm of rectifier166 Enabled(1) or Disabled (0)"
    ::= {psRelay4Masks 325}

r4VBV167Alarm OBJECT-TYPE
    SYNTAX   INTEGER{disabled(0), enabled(1)}
    MAX-ACCESS  read-write
    STATUS   current
    DESCRIPTION "Alarm of rectifier167 Enabled(1) or Disabled (0)"
    ::= {psRelay4Masks 326}

r4VBV168Alarm OBJECT-TYPE
    SYNTAX   INTEGER{disabled(0), enabled(1)}
    MAX-ACCESS  read-write
    STATUS   current
    DESCRIPTION "Alarm of rectifier168 Enabled(1) or Disabled (0)"
    ::= {psRelay4Masks 327}

r4VBV169Alarm OBJECT-TYPE
    SYNTAX   INTEGER{disabled(0), enabled(1)}
    MAX-ACCESS  read-write
    STATUS   current
    DESCRIPTION "Alarm of rectifier169 Enabled(1) or Disabled (0)"
    ::= {psRelay4Masks 328}

r4VBV170Alarm OBJECT-TYPE
    SYNTAX   INTEGER{disabled(0), enabled(1)}
    MAX-ACCESS  read-write
    STATUS   current
    DESCRIPTION "Alarm of rectifier170 Enabled(1) or Disabled (0)"
    ::= {psRelay4Masks 329}

r4VBV171Alarm OBJECT-TYPE
    SYNTAX   INTEGER{disabled(0), enabled(1)}
    MAX-ACCESS  read-write
    STATUS   current
    DESCRIPTION "Alarm of rectifier171 Enabled(1) or Disabled (0)"
    ::= {psRelay4Masks 330}

r4VBV172Alarm OBJECT-TYPE
    SYNTAX   INTEGER{disabled(0), enabled(1)}
    MAX-ACCESS  read-write
    STATUS   current
    DESCRIPTION "Alarm of rectifier172 Enabled(1) or Disabled (0)"
    ::= {psRelay4Masks 331}

r4VBV173Alarm OBJECT-TYPE
    SYNTAX   INTEGER{disabled(0), enabled(1)}
    MAX-ACCESS  read-write
    STATUS   current
    DESCRIPTION "Alarm of rectifier173 Enabled(1) or Disabled (0)"
    ::= {psRelay4Masks 332}

r4VBV174Alarm OBJECT-TYPE
    SYNTAX   INTEGER{disabled(0), enabled(1)}
    MAX-ACCESS  read-write
    STATUS   current
    DESCRIPTION "Alarm of rectifier174 Enabled(1) or Disabled (0)"
    ::= {psRelay4Masks 333}

r4VBV175Alarm OBJECT-TYPE
    SYNTAX   INTEGER{disabled(0), enabled(1)}
    MAX-ACCESS  read-write
    STATUS   current
    DESCRIPTION "Alarm of rectifier175 Enabled(1) or Disabled (0)"
    ::= {psRelay4Masks 334}

r4VBV176Alarm OBJECT-TYPE
    SYNTAX   INTEGER{disabled(0), enabled(1)}
    MAX-ACCESS  read-write
    STATUS   current
    DESCRIPTION "Alarm of rectifier176 Enabled(1) or Disabled (0)"
    ::= {psRelay4Masks 335}

r4VBV177Alarm OBJECT-TYPE
    SYNTAX   INTEGER{disabled(0), enabled(1)}
    MAX-ACCESS  read-write
    STATUS   current
    DESCRIPTION "Alarm of rectifier177 Enabled(1) or Disabled (0)"
    ::= {psRelay4Masks 336}

r4VBV178Alarm OBJECT-TYPE
    SYNTAX   INTEGER{disabled(0), enabled(1)}
    MAX-ACCESS  read-write
    STATUS   current
    DESCRIPTION "Alarm of rectifier178 Enabled(1) or Disabled (0)"
    ::= {psRelay4Masks 337}

r4VBV179Alarm OBJECT-TYPE
    SYNTAX   INTEGER{disabled(0), enabled(1)}
    MAX-ACCESS  read-write
    STATUS   current
    DESCRIPTION "Alarm of rectifier179 Enabled(1) or Disabled (0)"
    ::= {psRelay4Masks 338}

r4VBV180Alarm OBJECT-TYPE
    SYNTAX   INTEGER{disabled(0), enabled(1)}
    MAX-ACCESS  read-write
    STATUS   current
    DESCRIPTION "Alarm of rectifier180 Enabled(1) or Disabled (0)"
    ::= {psRelay4Masks 339}

r4VBVNoReserve OBJECT-TYPE
    SYNTAX   INTEGER{disabled(0), enabled(1)}
    MAX-ACCESS  read-write
    STATUS   current
    DESCRIPTION "Enabled(1) or Disabled (0)"
    ::= {psRelay4Masks 340}

r4VBVHighEfficiency OBJECT-TYPE
    SYNTAX   INTEGER{disabled(0), enabled(1)}
    MAX-ACCESS  read-write
    STATUS   current
    DESCRIPTION "Enabled(1) or Disabled (0)"
    ::= {psRelay4Masks 341}

--PhasesAlarm in psRelay4Masks
r4Phase1Alarm OBJECT-TYPE
    SYNTAX   INTEGER{disabled(0), enabled(1)}
    MAX-ACCESS  read-write
    STATUS   current
    DESCRIPTION "Enabled(1) or Disabled (0)"
    ::= {psRelay4Masks 352}

r4Phase2Alarm OBJECT-TYPE
    SYNTAX   INTEGER{disabled(0), enabled(1)}
    MAX-ACCESS  read-write
    STATUS   current
    DESCRIPTION "Enabled(1) or Disabled (0)"
    ::= {psRelay4Masks 353}

r4Phase3Alarm OBJECT-TYPE
    SYNTAX   INTEGER{disabled(0), enabled(1)}
    MAX-ACCESS  read-write
    STATUS   current
    DESCRIPTION "Enabled(1) or Disabled (0)"
    ::= {psRelay4Masks 354}

r4MainsSensorError OBJECT-TYPE
    SYNTAX   INTEGER{disabled(0), enabled(1)}
    MAX-ACCESS  read-write
    STATUS   current
    DESCRIPTION "Enabled(1) or Disabled (0)"
    ::= {psRelay4Masks 355}

r4LightProtectionAlarm OBJECT-TYPE
    SYNTAX   INTEGER{disabled(0), enabled(1)}
    MAX-ACCESS  read-write
    STATUS   current
    DESCRIPTION "Enabled(1) or Disabled (0)"
    ::= {psRelay4Masks 356}

--Ambience Temperature in psRelay4Masks
r4LowTemperature OBJECT-TYPE
    SYNTAX   INTEGER{disabled(0), enabled(1)}
    MAX-ACCESS  read-write
    STATUS   current
    DESCRIPTION "Enabled(1) or Disabled (0)"
    ::= {psRelay4Masks 384}

r4HighTemperature OBJECT-TYPE
    SYNTAX   INTEGER{disabled(0), enabled(1)}
    MAX-ACCESS  read-write
    STATUS   current
    DESCRIPTION "Enabled(1) or Disabled (0)"
    ::= {psRelay4Masks 385}

r4TemperatureSensorError OBJECT-TYPE
    SYNTAX   INTEGER{disabled(0), enabled(1)}
    MAX-ACCESS  read-write
    STATUS   current
    DESCRIPTION "Enabled(1) or Disabled (0)"
    ::= {psRelay4Masks 386}

--DryContacts in psRelay4Masks
r4DryContact1 OBJECT-TYPE
    SYNTAX   INTEGER{disabled(0), enabled(1)}
    MAX-ACCESS  read-write
    STATUS   current
    DESCRIPTION "Enabled(1) or Disabled (0)"
    ::= {psRelay4Masks 416}

r4DryContact2 OBJECT-TYPE
    SYNTAX   INTEGER{disabled(0), enabled(1)}
    MAX-ACCESS  read-write
    STATUS   current
    DESCRIPTION "Enabled(1) or Disabled (0)"
    ::= {psRelay4Masks 417}

r4DryContact3 OBJECT-TYPE
    SYNTAX   INTEGER{disabled(0), enabled(1)}
    MAX-ACCESS  read-write
    STATUS   current
    DESCRIPTION "Enabled(1) or Disabled (0)"
    ::= {psRelay4Masks 418}

r4DryContact4 OBJECT-TYPE
    SYNTAX   INTEGER{disabled(0), enabled(1)}
    MAX-ACCESS  read-write
    STATUS   current
    DESCRIPTION "Enabled(1) or Disabled (0)"
    ::= {psRelay4Masks 419}

r4DryContact5 OBJECT-TYPE
    SYNTAX   INTEGER{disabled(0), enabled(1)}
    MAX-ACCESS  read-write
    STATUS   current
    DESCRIPTION "Enabled(1) or Disabled (0)"
    ::= {psRelay4Masks 420}

r4DryContact6 OBJECT-TYPE
    SYNTAX   INTEGER{disabled(0), enabled(1)}
    MAX-ACCESS  read-write
    STATUS   current
    DESCRIPTION "Enabled(1) or Disabled (0)"
    ::= {psRelay4Masks 421}

r4DryContact7 OBJECT-TYPE
    SYNTAX   INTEGER{disabled(0), enabled(1)}
    MAX-ACCESS  read-write
    STATUS   current
    DESCRIPTION "Enabled(1) or Disabled (0)"
    ::= {psRelay4Masks 422}

r4DryContact8 OBJECT-TYPE
    SYNTAX   INTEGER{disabled(0), enabled(1)}
    MAX-ACCESS  read-write
    STATUS   current
    DESCRIPTION "Enabled(1) or Disabled (0)"
    ::= {psRelay4Masks 423}

r4DryContact9 OBJECT-TYPE
    SYNTAX   INTEGER{disabled(0), enabled(1)}
    MAX-ACCESS  read-write
    STATUS   current
    DESCRIPTION "Enabled(1) or Disabled (0)"
    ::= {psRelay4Masks 424}

r4DryContact10 OBJECT-TYPE
    SYNTAX   INTEGER{disabled(0), enabled(1)}
    MAX-ACCESS  read-write
    STATUS   current
    DESCRIPTION "Enabled(1) or Disabled (0)"
    ::= {psRelay4Masks 425}

r4DryContact11 OBJECT-TYPE
    SYNTAX   INTEGER{disabled(0), enabled(1)}
    MAX-ACCESS  read-write
    STATUS   current
    DESCRIPTION "Enabled(1) or Disabled (0)"
    ::= {psRelay4Masks 426}

r4DryContact12 OBJECT-TYPE
    SYNTAX   INTEGER{disabled(0), enabled(1)}
    MAX-ACCESS  read-write
    STATUS   current
    DESCRIPTION "Enabled(1) or Disabled (0)"
    ::= {psRelay4Masks 427}

r4DryContact13 OBJECT-TYPE
    SYNTAX   INTEGER{disabled(0), enabled(1)}
    MAX-ACCESS  read-write
    STATUS   current
    DESCRIPTION "Enabled(1) or Disabled (0)"
    ::= {psRelay4Masks 428}

r4DryContact14 OBJECT-TYPE
    SYNTAX   INTEGER{disabled(0), enabled(1)}
    MAX-ACCESS  read-write
    STATUS   current
    DESCRIPTION "Enabled(1) or Disabled (0)"
    ::= {psRelay4Masks 429}

r4DryContact15 OBJECT-TYPE
    SYNTAX   INTEGER{disabled(0), enabled(1)}
    MAX-ACCESS  read-write
    STATUS   current
    DESCRIPTION "Enabled(1) or Disabled (0)"
    ::= {psRelay4Masks 430}

r4DryContact16 OBJECT-TYPE
    SYNTAX   INTEGER{disabled(0), enabled(1)}
    MAX-ACCESS  read-write
    STATUS   current
    DESCRIPTION "Enabled(1) or Disabled (0)"
    ::= {psRelay4Masks 431}

-- --------------------------------------

r4BatteryLiIonAlarm OBJECT-TYPE  
    SYNTAX   INTEGER{disabled(0), enabled(1)}
    MAX-ACCESS  read-write
    STATUS   current
    DESCRIPTION "Enabled(1) or Disabled (0)"
    ::= {psRelay4Masks 480}

--нет связи с BMS
r4BatteryBMSComFail OBJECT-TYPE  
    SYNTAX   INTEGER{disabled(0), enabled(1)}
    MAX-ACCESS  read-write
    STATUS   current
    DESCRIPTION "Enabled(1) or Disabled (0)"
    ::= {psRelay4Masks 481}

-- --------------------------------------

--Alarm Masks (end of block) ^^^^^^^^^^^^^^^^^^^^^^^^^^^^^^^^^^^^^^^^^^^^^^^^^^^^^^^^^^^^^^^^^^^^^^^^^^^
	
--BattarySettings

stFloatVoltage OBJECT-TYPE
	SYNTAX			INTEGER
	MAX-ACCESS		read-write
	STATUS			current
	DESCRIPTION		"x0.01 (5400 = 54.01 V)"
	::= {psBatterySettings 1}

stBoostVoltage OBJECT-TYPE
	SYNTAX			INTEGER
	MAX-ACCESS		read-write
	STATUS			current
	DESCRIPTION		"x0.01 (5400 = 54.01 V)"
	::= {psBatterySettings 2}

stBoostEnable OBJECT-TYPE
	SYNTAX			INTEGER{disabled(0), enabled(1)}
	MAX-ACCESS		read-write
	STATUS			current
	DESCRIPTION		"Enabled(1) or Disabled (0)"
	::= {psBatterySettings 3}

stEqualizeVoltage OBJECT-TYPE
	SYNTAX			INTEGER
	MAX-ACCESS		read-write
	STATUS			current
	DESCRIPTION		"x0.01 (5400 = 54.01 V)"
	::= {psBatterySettings 4}


stEndTestVoltage OBJECT-TYPE
	SYNTAX			INTEGER
	MAX-ACCESS		read-write
	STATUS			current
	DESCRIPTION		"x0.01 (5400 = 54.01 V)"
	::= {psBatterySettings 5}

stCriticalLowVoltage OBJECT-TYPE
	SYNTAX			INTEGER
	MAX-ACCESS		read-write
	STATUS			current
	DESCRIPTION		"x0.01 (5400 = 54.01 V)"
	::= {psBatterySettings 6}

stTermocompensationEnable OBJECT-TYPE
	SYNTAX			INTEGER
	MAX-ACCESS		read-write
	STATUS			current
	DESCRIPTION		"Enabled(1) or Disabled (0)"
	::= {psBatterySettings 7}

stTermocompensationCoefficient OBJECT-TYPE
	SYNTAX			INTEGER
	MAX-ACCESS		read-write
	STATUS			current
	DESCRIPTION		"3..8 (3 = 3 mv/el/C)"
	::= {psBatterySettings 8}


stChargeCurrentLimit OBJECT-TYPE
	SYNTAX			INTEGER
	MAX-ACCESS		read-write
	STATUS			current
	DESCRIPTION		"x0.01C10 (100 = 0.10C10)"
	::= {psBatterySettings 9}


stGroupCapacity OBJECT-TYPE
	SYNTAX			INTEGER
	MAX-ACCESS		read-write
	STATUS			current
	DESCRIPTION		"Capacity of one battery group in Ah (100 = 100Ah)"
	::= {psBatterySettings 10}

stEqualizeTime OBJECT-TYPE
    SYNTAX			INTEGER(1..24)
	MAX-ACCESS		read-write
	STATUS			current
	DESCRIPTION		"Time of Eq Charging, 1 hour"
	::= {psBatterySettings 11}

stFastChTime OBJECT-TYPE
    SYNTAX			INTEGER(0..24)
	MAX-ACCESS		read-write
	STATUS			current
	DESCRIPTION		"Time of Fast Charging, 1 hour. If 0 is set, fast charging timer is off"
	::= {psBatterySettings 12}

stPeriodTestEnable OBJECT-TYPE
    SYNTAX			INTEGER{disabled(0), enabled(1)}
	MAX-ACCESS		read-write
	STATUS			current
	DESCRIPTION		"Enabled(1) or Disabled (0)"
	::= {psBatterySettings 13}

stTestPeriod OBJECT-TYPE
    SYNTAX          INTEGER(1..12)
    MAX-ACCESS      read-write
    STATUS          current
    DESCRIPTION     "Test period, 1 month"
	::= {psBatterySettings 14}

stTestStartTime OBJECT-TYPE
	SYNTAX			OCTET STRING (SIZE (14))
	MAX-ACCESS		read-write
	STATUS			current
	DESCRIPTION		"Battery Test Start Time UTC time in format DDMMYYYYhhmmss"
	::= {psBatterySettings 15}

stFixedLoadCurEnable OBJECT-TYPE
    SYNTAX			INTEGER{disabled(0), enabled(1)}
	MAX-ACCESS		read-write
	STATUS			current
	DESCRIPTION		"Enabled(1) or Disabled (0)"
	::= {psBatterySettings 16}

stFixedLoadCur OBJECT-TYPE
    SYNTAX			INTEGER
	MAX-ACCESS		read-write
	STATUS			current
	DESCRIPTION		"Fixed load current (5..5000 A)"
	::= {psBatterySettings 17}

stDischCur OBJECT-TYPE
    SYNTAX			INTEGER
	MAX-ACCESS		read-write
	STATUS			current
	DESCRIPTION		"Discharge current, x0,01 C10 (1 = 0,01 C10)"
	::= {psBatterySettings 18}

-- ShortTestSettings

stShortTestVoltage OBJECT-TYPE
    SYNTAX          INTEGER
    MAX-ACCESS      read-write
    STATUS          current
    DESCRIPTION     "x0.1 (5400 = 54.01 V)"
    ::= {psBatteryShortTestSettings 1}
    
stShortTestTimer OBJECT-TYPE
    SYNTAX          INTEGER(1..720)
    MAX-ACCESS      read-write
    STATUS          current
    DESCRIPTION     "Short Test timer, 1 minute"
    ::= {psBatteryShortTestSettings 2}
    
stShortTestPeriod OBJECT-TYPE
    SYNTAX          INTEGER(1..60)
    MAX-ACCESS      read-write
    STATUS          current
    DESCRIPTION     "Short Test period, 1 day"
    ::= {psBatteryShortTestSettings 3}
    
stShortTestEnable OBJECT-TYPE
	SYNTAX			INTEGER{disabled(0), enabled(1)}
	MAX-ACCESS		read-write
	STATUS			current
	DESCRIPTION		"Enabled(1) or Disabled (0)"
    ::= {psBatteryShortTestSettings 4}

stShortTestStartTime OBJECT-TYPE
	SYNTAX			OCTET STRING (SIZE (14))
	MAX-ACCESS		read-write
	STATUS			current
	DESCRIPTION		"Short Battery Test Start Time UTC time in format DDMMYYYYhhmmss"
	::= {psBatteryShortTestSettings 5}

-- ContactorSettings

stBLVDDisconnectedVoltage OBJECT-TYPE
	SYNTAX			INTEGER
	MAX-ACCESS		read-write
	STATUS			current
	DESCRIPTION		"Voltage of BLVD disconected, 0.01 V (4600 = 46,00 V)"
	::= {psContactorSettings 1}

stLLVD1DisconnectedVoltage OBJECT-TYPE
	SYNTAX			INTEGER
	MAX-ACCESS		read-write
	STATUS			current
	DESCRIPTION		"Voltage of LLVD1 disconected, 0.01 V (4600 = 46,00 V)"
	::= {psContactorSettings 2}

stLLVD2DisconnectedVoltage OBJECT-TYPE
	SYNTAX			INTEGER
	MAX-ACCESS		read-write
	STATUS			current
	DESCRIPTION		"Voltage of LLVD2 disconected, 0.01 V (4600 = 46,00 V)"
	::= {psContactorSettings 3}

stLLVD3DisconnectedVoltage OBJECT-TYPE
	SYNTAX			INTEGER
	MAX-ACCESS		read-write
	STATUS			current
	DESCRIPTION		"Voltage of LLVD2 disconected, 0.01 V (4600 = 46,00 V)"
	::= {psContactorSettings 4}

stBLVDDisconnectedTime OBJECT-TYPE
	SYNTAX			INTEGER(1..720)
	MAX-ACCESS		read-write
	STATUS			current	
	DESCRIPTION		"Time of BLVD disconnected, 1 minute"
	::= {psContactorSettings 5}

stLLVD1DisconnectedTime OBJECT-TYPE
	SYNTAX			INTEGER(1..720)
	MAX-ACCESS		read-write
	STATUS			current	
	DESCRIPTION		"Time of LLVD1 disconnected, 1 minute"
	::= {psContactorSettings 6}

stLLVD2DisconnectedTime OBJECT-TYPE
	SYNTAX			INTEGER(1..720)
	MAX-ACCESS		read-write
	STATUS			current	
	DESCRIPTION		"Time of LLVD2 disconnected, 1 minute"
	::= {psContactorSettings 7}

stLLVD3DisconnectedTime OBJECT-TYPE
	SYNTAX			INTEGER(1..720)
	MAX-ACCESS		read-write
	STATUS			current	
	DESCRIPTION		"Time of LLVD3 disconnected, 1 minute"
	::= {psContactorSettings 8}


stBLVDDisconnectedCapacity OBJECT-TYPE
	SYNTAX			INTEGER(1..99)
	MAX-ACCESS		read-write
	STATUS			current	
	DESCRIPTION		"Capacity of BLVD disconnected, 1 %"
	::= {psContactorSettings 9}

stLLVD1DisconnectedCapacity OBJECT-TYPE
	SYNTAX			INTEGER(1..99)
	MAX-ACCESS		read-write
	STATUS			current	
	DESCRIPTION		"Capacity of LLVD1 disconnected, 1 %"
	::= {psContactorSettings 10}

stLLVD2DisconnectedCapacity OBJECT-TYPE
	SYNTAX			INTEGER(1..99)
	MAX-ACCESS		read-write
	STATUS			current	
	DESCRIPTION		"Capacity of LLVD2 disconnected, 1 %"
	::= {psContactorSettings 11}

stLLVD3DisconnectedCapacity OBJECT-TYPE
	SYNTAX			INTEGER(1..99)
	MAX-ACCESS		read-write
	STATUS			current	
	DESCRIPTION		"Capacity of LLVD3 disconnected, 1 %"
	::= {psContactorSettings 12}

stContactorControl OBJECT-TYPE
	SYNTAX			INTEGER{auto(0), manual(1)}
	MAX-ACCESS		read-write
	STATUS			current
	DESCRIPTION		"Manual(1) or Auto(0)"
    ::= {psContactorSettings 13}

--MainsSettings

stLowMainsVoltageTherehold OBJECT-TYPE
	SYNTAX			INTEGER(170..210)
	MAX-ACCESS		read-write
	STATUS			current
	DESCRIPTION		"Low phases voltage alarm therehold, V (170 = 170 V)"
	::= {psMainsSettings 1}

stHightMainsVoltageTherehold OBJECT-TYPE
	SYNTAX			INTEGER(230..290)
	MAX-ACCESS		read-write
	STATUS			current
	DESCRIPTION		"Hight phases voltage alarm therehold, V (290 = 290 V)"
	::= {psMainsSettings 2}

--TemperatureSettings

stNumberTemperatureSensors OBJECT-TYPE
	SYNTAX			INTEGER(1..2)
	MAX-ACCESS		read-write
	STATUS			current
	DESCRIPTION		"Number of temperature sensors 1 -sensor for termocompensation, 2 - sensor for ambient (options)"
	::= {psTemperatureSettings 1}

stLowTemperatureTherehold OBJECT-TYPE
	SYNTAX			INTEGER
	MAX-ACCESS		read-write
	STATUS			current
	DESCRIPTION		"Low temperature sensor therehold, 0.1 deg.C (100 = 10 deg.C)"
	::= {psTemperatureSettings 2}

stHightTemperatureTherehold OBJECT-TYPE
	SYNTAX			INTEGER
	MAX-ACCESS		read-write
	STATUS			current
	DESCRIPTION		"Hight temperature sensor therehold, 0.1 deg.C (350 = 35 deg.C)"
	::= {psTemperatureSettings 3}

stTemperatureGisteresis OBJECT-TYPE
	SYNTAX			INTEGER
	MAX-ACCESS		read-write
	STATUS			current
	DESCRIPTION		"Gisteresis of temperature, 0.1 deg.C (20 = 2.0 deg.C)"
	::= {psTemperatureSettings 4}

--psConfiguration

stBatteryGroupsNumber OBJECT-TYPE
	SYNTAX			INTEGER(0..4)
	MAX-ACCESS		read-write
	STATUS			current
	DESCRIPTION		"Number of battery groups"
	::= {psConfiguration 1}
	
stLoadFusesNumber OBJECT-TYPE
	SYNTAX			INTEGER(1..52)
	MAX-ACCESS		read-write
	STATUS			current
	DESCRIPTION		"Number of load fuses"
	::= {psConfiguration 2}	
	

stLVDsNumber OBJECT-TYPE
	SYNTAX			INTEGER{none(0), blvdonly(1), blvdandllvd1(2), blvdandllvd1andllvd2(3)}
	MAX-ACCESS		read-write
	STATUS			current
	DESCRIPTION		"Number of contactors LVD, 0-None, 1-BLVD only, 2-BLVD and LLVD1, 3-BLVD and LLVD1 and LLVD2"
	::= {psConfiguration 3}

stVBVNumber OBJECT-TYPE
	SYNTAX			INTEGER(1..180)
	MAX-ACCESS		read-write
	STATUS			current
	DESCRIPTION		"Number of rectifiers"
	::= {psConfiguration 4}

--psNetworkSettings

stIPaddress OBJECT-TYPE
	SYNTAX			IpAddress
	MAX-ACCESS		read-write
	STATUS			current
	DESCRIPTION		"IP address in format xxx.xxx.xxx.xxx, example 192.168.000.064"
	::= {psNetworkSettings 1}
	
stNetworkMask OBJECT-TYPE
	SYNTAX			IpAddress
	MAX-ACCESS		read-write
	STATUS			current
	DESCRIPTION		"Network mask  in format xxx.xxx.xxx.xxx, example 255.255.255.000"
	::= {psNetworkSettings 2}	

stNetworkGateway OBJECT-TYPE
	SYNTAX			IpAddress
	MAX-ACCESS		read-write
	STATUS			current
	DESCRIPTION		"Network Gateway in format xxx.xxx.xxx.xxx, example 192.168.000.064"
	::= {psNetworkSettings 3}
	
--SecuritySettings

stMonitoringPassword OBJECT-TYPE
	SYNTAX			OCTET STRING (SIZE (6))
	MAX-ACCESS		read-write
	STATUS			current
	DESCRIPTION		"Password for monitoring by ModbusTCP, USB, RS485"
	::= {psSecuritySettings 1}
	
stEnableRemouteChangeSetting OBJECT-TYPE
	SYNTAX			INTEGER{disabled(0), enabled(1)}
	MAX-ACCESS		read-write
	STATUS			current
	DESCRIPTION		"Enable(1) or Disable(0) change settings remoutly"
	::= {psSecuritySettings 2}

stEnableRemouteUpdateFirmware OBJECT-TYPE
	SYNTAX			INTEGER{disabled(0), enabled(1)}
	MAX-ACCESS		read-write
	STATUS			current
	DESCRIPTION		"Enable(1) or Disable(0) update  settings by Ethernet"
	::= {psSecuritySettings 3}

--psSNMPSettings

stSNMPVersion OBJECT-TYPE
	SYNTAX			INTEGER{snmpv2c(1), snmpv3(3)}
	MAX-ACCESS		read-write
	STATUS			current
	DESCRIPTION		"1-SNMPv2C, 3-SNMPv3"
	::= {psSNMPSettings 1}

stSNMPAdministratorName OBJECT-TYPE
	SYNTAX			OCTET STRING (SIZE (10))
	MAX-ACCESS		read-write
	STATUS			current
	DESCRIPTION		"Name of Administator user for SNMPv3. Min 8, max 10 characters, 0-1, a-z, A-z"
	::= {psSNMPSettings 2}

stSNMPAdministratorAuthPassword OBJECT-TYPE
	SYNTAX			OCTET STRING (SIZE (10))
	MAX-ACCESS		read-write
	STATUS			current
	DESCRIPTION		"Authentification password of Administator   for SNMPv3. Min 8, max 10 characters, 0-1, a-z, A-z, :;<=>?@[\]^_'{|}~"
	::= {psSNMPSettings 3}
	
stSNMPAdministratorPrivPassword OBJECT-TYPE
	SYNTAX			OCTET STRING (SIZE (10))
	MAX-ACCESS		read-write
	STATUS			current
	DESCRIPTION		"Private password of Administator for SNMPv3. Min 8, max 10 characters, 0-1, a-z, A-z, :;<=>?@[\]^_'{|}~"
	::= {psSNMPSettings 4}	
	
	
stSNMPEngineerName OBJECT-TYPE
	SYNTAX			OCTET STRING (SIZE (10))
	MAX-ACCESS		read-write
	STATUS			current
	DESCRIPTION		"Name of Engineer user for SNMPv3. Min 8, max 10 characters, 0-1, a-z, A-z"
	::= {psSNMPSettings 5}

stSNMPEngineerAuthPassword OBJECT-TYPE
	SYNTAX			OCTET STRING (SIZE (10))
	MAX-ACCESS		read-write
	STATUS			current
	DESCRIPTION		"Authentification password of Engineer user for SNMPv3. Min 8, max 10 characters, 0-1, a-z, A-z, :;<=>?@[\]^_'{|}~"
	::= {psSNMPSettings 6}

stSNMPEngineerPrivPassword OBJECT-TYPE
	SYNTAX			OCTET STRING (SIZE (10))
	MAX-ACCESS		read-write
	STATUS			current
	DESCRIPTION		"Private password of Engineer user for SNMPv3. Min 8, max 10 characters, 0-1, a-z, A-z, :;<=>?@[\]^_'{|}~"
	::= {psSNMPSettings 7}

stSNMPOperatorName OBJECT-TYPE
	SYNTAX			OCTET STRING (SIZE (10))
	MAX-ACCESS		read-write
	STATUS			current
	DESCRIPTION		"Name of Operator user for SNMPv3. Min 8, max 10 characters, 0-1, a-z, A-z"
	::= {psSNMPSettings 8}

stSNMPOperatorAuthPassword OBJECT-TYPE
	SYNTAX			OCTET STRING (SIZE (10))
	MAX-ACCESS		read-write
	STATUS			current
	DESCRIPTION		"Authentification password of Operator user for SNMPv3. Min 8, max 10 characters, 0-1, a-z, A-z, :;<=>?@[\]^_'{|}~"
	::= {psSNMPSettings 9}	

stSNMPOperatorPrivPassword OBJECT-TYPE
	SYNTAX			OCTET STRING (SIZE (10))
	MAX-ACCESS		read-write
	STATUS			current
	DESCRIPTION		"Private password of Operator user for SNMPv3. Min 8, max 10 characters, 0-1, a-z, A-z, :;<=>?@[\]^_'{|}~"
	::= {psSNMPSettings 10}	

	
stSNMPSAuthAlgo OBJECT-TYPE
	SYNTAX			INTEGER{none(0), md5(1), sha1(2)}
	MAX-ACCESS		read-write
	STATUS			current
	DESCRIPTION		"Algorithm for audentification: None(0), MD5(1), SHA1(2)"
	::= {psSNMPSettings 11}	

stSNMPSPrivAlgo OBJECT-TYPE
	SYNTAX			INTEGER{none(0), des(1), aes128(2)}
	MAX-ACCESS		read-write
	STATUS			current
	DESCRIPTION		"Algorithm for private: (none(0), DES-CBC(1), AES-128-CFB(2)) "
	::= {psSNMPSettings 12}		

stSNMPReadComunity OBJECT-TYPE
	SYNTAX			OCTET STRING (SIZE (9))
	MAX-ACCESS		read-write
	STATUS			current
	DESCRIPTION		"ReadComunity for SNMP v2C. Min 6, max 9 characters"
	::= {psSNMPSettings 13}	

stSNMPWriteComunity OBJECT-TYPE
	SYNTAX			OCTET STRING (SIZE (9))
	MAX-ACCESS		read-write
	STATUS			current
	DESCRIPTION		"Write Comunity for SNMP v2C. Min 6, max 9 characters"
	::= {psSNMPSettings 14}
	

stSNMPTrap1ServerIP OBJECT-TYPE
	SYNTAX			IpAddress
	MAX-ACCESS		read-write
	STATUS			current
	DESCRIPTION		"IP address 1 for send trap, in format xxx.xxx.xxx.xxx, example 192.168.000.064"
	::= {psSNMPSettings 15}	

stSNMPTrap2ServerIP OBJECT-TYPE
	SYNTAX			IpAddress
	MAX-ACCESS		read-write
	STATUS			current
	DESCRIPTION		"IP address 1 for send trap, in format xxx.xxx.xxx.xxx, example 192.168.000.064"
	::= {psSNMPSettings 16}	

stSNMPTrap3ServerIP OBJECT-TYPE
	SYNTAX			IpAddress
	MAX-ACCESS		read-write
	STATUS			current
	DESCRIPTION		"IP address 1 for send trap, in format xxx.xxx.xxx.xxx, example 192.168.000.064"
	::= {psSNMPSettings 17}	

--stSNMPTrap4ServerIP OBJECT-TYPE
--	SYNTAX			IpAddress
--	MAX-ACCESS		read-write
--	STATUS			current
--	DESCRIPTION		"IP address 1 for send trap"
--	::= {psSNMPSettings 18}		

stSNMPTrap1Enable OBJECT-TYPE
	SYNTAX			INTEGER{disabled(0), enabled(1)}
	MAX-ACCESS		read-write
	STATUS			current
	DESCRIPTION		"Enable(1) or Disable(0) send traps to IP address 1"
	::= {psSNMPSettings 19}	

stSNMPTrap2Enable OBJECT-TYPE
	SYNTAX			INTEGER{disabled(0), enabled(1)}
	MAX-ACCESS		read-write
	STATUS			current
	DESCRIPTION		"Enable(1) or Disable(0) send traps to IP address 1"
	::= {psSNMPSettings 20}
	
stSNMPTrap3Enable OBJECT-TYPE
	SYNTAX			INTEGER{disabled(0), enabled(1)}
	MAX-ACCESS		read-write
	STATUS			current
	DESCRIPTION		"Enable(1) or Disable(0) send traps to IP address 1"
	::= {psSNMPSettings 21}

--stSNMPTrap4Enable OBJECT-TYPE
--	SYNTAX			INTEGER
--	MAX-ACCESS		read-write
--	STATUS			current
--	DESCRIPTION		"Enable(1) or Disable(0) send traps to IP address 1"
--	::= {psSNMPSettings 22}


----------------------------------------------------------------------------
--BMS

--psBMSType OBJECT-TYPE
--	SYNTAX			INTEGER{none(0), ZTT(1), Delta(2)}
--	MAX-ACCESS		read-only
--	STATUS			current
--	DESCRIPTION		"Li-Ion Type: None(0), ZTT(1), Delta(2)"
--	::= {psBMS 1}	

psBMSTable OBJECT-TYPE
	SYNTAX			SEQUENCE OF PSBMSEntry
	MAX-ACCESS		not-accessible
	STATUS			current
	DESCRIPTION		"status of BMS."
	::= {psBMS 1}

psBMSEntry OBJECT-TYPE
	SYNTAX			PSBMSEntry
	MAX-ACCESS		not-accessible
	STATUS			current
	DESCRIPTION		""
	INDEX {psBMSNumber}
	::= {psBMSTable 1}

PSBMSEntry ::= SEQUENCE
	{
		psBMSNumber		    INTEGER,
		psBMSVoltage		INTEGER,
		psBMSCurrent		INTEGER,
		psBMSStatus		    INTEGER,
        psBMSSubStatus      INTEGER,
        psBMSIntTemperature INTEGER,
        psBMSExtTemperature INTEGER,
        psBMSCap            INTEGER,
        psBMSRemainCap      INTEGER,
        psBMSCycles         INTEGER,
        psBMSCells          INTEGER,
        psBMSCellVoltMin    INTEGER,
        psBMSCellVoltMax    INTEGER,
        psBMSCellVoltDiff   INTEGER,
        psBMSCell1Voltage   INTEGER,
        psBMSCell2Voltage   INTEGER,
        psBMSCell3Voltage   INTEGER,
        psBMSCell4Voltage   INTEGER,
        psBMSCell5Voltage   INTEGER,
        psBMSCell6Voltage   INTEGER,
        psBMSCell7Voltage   INTEGER,
        psBMSCell8Voltage   INTEGER,
        psBMSCell9Voltage   INTEGER,
        psBMSCell10Voltage  INTEGER,
        psBMSCell11Voltage  INTEGER,
        psBMSCell12Voltage  INTEGER,
        psBMSCell13Voltage  INTEGER,
        psBMSCell14Voltage  INTEGER,
        psBMSCell15Voltage  INTEGER,
        psBMSCell16Voltage  INTEGER
	}

psBMSNumber OBJECT-TYPE
	SYNTAX			INTEGER (1..16)
	MAX-ACCESS		read-only
	STATUS			current
	DESCRIPTION		"BMS number."
	::= {psBMSEntry 1}

psBMSVoltage OBJECT-TYPE
	SYNTAX			INTEGER
	UNITS			"0.01V"
	MAX-ACCESS		read-only
	STATUS			current
	DESCRIPTION		"BMS output voltage in 0.01V."
	::= {psBMSEntry 2}

psBMSCurrent OBJECT-TYPE
	SYNTAX			INTEGER
	UNITS			"0.001A"
	MAX-ACCESS		read-only
	STATUS			current
	DESCRIPTION		"BMS output current in 0.01A."
	::= {psBMSEntry 3}

psBMSStatus OBJECT-TYPE
	SYNTAX			INTEGER {normal(0), alarm(1), absent(2)}
	MAX-ACCESS		read-only
	STATUS			current
	DESCRIPTION		"BMS status. If status absent(2) the values of Voltage, Current, etc. shold be discarded."
	::= {psBMSEntry 4}

psBMSSubStatus OBJECT-TYPE
	SYNTAX			INTEGER {stand-by(0), charge(1), discharge(2)}
	MAX-ACCESS		read-only
	STATUS			current
	DESCRIPTION		"BMS substatus."
	::= {psBMSEntry 5}

psBMSIntTemperature OBJECT-TYPE
	SYNTAX			INTEGER
	UNITS			"0.1degC"
	MAX-ACCESS		read-only
	STATUS			current
	DESCRIPTION		"BMS internal temperature sensor, 0.1dgC."
	::= {psBMSEntry 6}

psBMSExtTemperature OBJECT-TYPE
	SYNTAX			INTEGER
	UNITS			"0.1degC"
	MAX-ACCESS		read-only
	STATUS			current
	DESCRIPTION		"BMS external temperature sensor, 0.1dgC."
	::= {psBMSEntry 7}      

psBMSCap OBJECT-TYPE
	SYNTAX			INTEGER
	UNITS			"0.01Ah"
	MAX-ACCESS		read-only
	STATUS			current
	DESCRIPTION		"BMS capacity, 0.01Ah."
	::= {psBMSEntry 8} 

psBMSRemainCap OBJECT-TYPE
	SYNTAX			INTEGER
	UNITS			"0.01Ah"
	MAX-ACCESS		read-only
	STATUS			current
	DESCRIPTION		"BMS remain capacity, 0.01Ah."
	::= {psBMSEntry 9}

psBMSCycles OBJECT-TYPE
	SYNTAX			INTEGER
	MAX-ACCESS		read-only
	STATUS			current
	DESCRIPTION		"BMS cycles."
	::= {psBMSEntry 10}

psBMSCells OBJECT-TYPE
	SYNTAX			INTEGER (1..16)
	MAX-ACCESS		read-only
	STATUS			current
	DESCRIPTION		"BMS cells number."
	::= {psBMSEntry 11}

psBMSCellVoltMin OBJECT-TYPE
	SYNTAX			INTEGER
	UNITS			"0.001V"
	MAX-ACCESS		read-only
	STATUS			current
	DESCRIPTION		"BMS output voltage in 0.001V."
	::= {psBMSEntry 12}

psBMSCellVoltMax OBJECT-TYPE
	SYNTAX			INTEGER
	UNITS			"0.001V"
	MAX-ACCESS		read-only
	STATUS			current
	DESCRIPTION		"BMS output voltage in 0.001V."
	::= {psBMSEntry 13}

psBMSCellVoltDiff OBJECT-TYPE
	SYNTAX			INTEGER
	UNITS			"0.001V"
	MAX-ACCESS		read-only
	STATUS			current
	DESCRIPTION		"BMS output voltage in 0.001V."
	::= {psBMSEntry 14}

psBMSCell1Voltage OBJECT-TYPE
	SYNTAX			INTEGER
	UNITS			"0.001V"
	MAX-ACCESS		read-only
	STATUS			current
	DESCRIPTION		"BMS cell 1 voltage in 0.001V."
	::= {psBMSEntry 15}

psBMSCell2Voltage OBJECT-TYPE
	SYNTAX			INTEGER
	UNITS			"0.001V"
	MAX-ACCESS		read-only
	STATUS			current
	DESCRIPTION		"BMS cell 2 voltage in 0.001V."
	::= {psBMSEntry 16}

psBMSCell3Voltage OBJECT-TYPE
	SYNTAX			INTEGER
	UNITS			"0.001V"
	MAX-ACCESS		read-only
	STATUS			current
	DESCRIPTION		"BMS cell 3 voltage in 0.001V."
	::= {psBMSEntry 17}

psBMSCell4Voltage OBJECT-TYPE
	SYNTAX			INTEGER
	UNITS			"0.001V"
	MAX-ACCESS		read-only
	STATUS			current
	DESCRIPTION		"BMS cell 4 voltage in 0.001V."
	::= {psBMSEntry 18}

psBMSCell5Voltage OBJECT-TYPE
	SYNTAX			INTEGER
	UNITS			"0.001V"
	MAX-ACCESS		read-only
	STATUS			current
	DESCRIPTION		"BMS cell 5 voltage in 0.001V."
	::= {psBMSEntry 19}

psBMSCell6Voltage OBJECT-TYPE
	SYNTAX			INTEGER
	UNITS			"0.001V"
	MAX-ACCESS		read-only
	STATUS			current
	DESCRIPTION		"BMS cell 6 voltage in 0.001V."
	::= {psBMSEntry 20}

psBMSCell7Voltage OBJECT-TYPE
	SYNTAX			INTEGER
	UNITS			"0.001V"
	MAX-ACCESS		read-only
	STATUS			current
	DESCRIPTION		"BMS cell 7 voltage in 0.001V."
	::= {psBMSEntry 21}

psBMSCell8Voltage OBJECT-TYPE
	SYNTAX			INTEGER
	UNITS			"0.001V"
	MAX-ACCESS		read-only
	STATUS			current
	DESCRIPTION		"BMS cell 8 voltage in 0.001V."
	::= {psBMSEntry 22}

psBMSCell9Voltage OBJECT-TYPE
	SYNTAX			INTEGER
	UNITS			"0.001V"
	MAX-ACCESS		read-only
	STATUS			current
	DESCRIPTION		"BMS cell 9 voltage in 0.001V."
	::= {psBMSEntry 23}

psBMSCell10Voltage OBJECT-TYPE
	SYNTAX			INTEGER
	UNITS			"0.001V"
	MAX-ACCESS		read-only
	STATUS			current
	DESCRIPTION		"BMS cell 10 voltage in 0.001V."
	::= {psBMSEntry 24}

psBMSCell11Voltage OBJECT-TYPE
	SYNTAX			INTEGER
	UNITS			"0.001V"
	MAX-ACCESS		read-only
	STATUS			current
	DESCRIPTION		"BMS cell 11 voltage in 0.001V."
	::= {psBMSEntry 25}

psBMSCell12Voltage OBJECT-TYPE
	SYNTAX			INTEGER
	UNITS			"0.001V"
	MAX-ACCESS		read-only
	STATUS			current
	DESCRIPTION		"BMS cell 12 voltage in 0.001V."
	::= {psBMSEntry 26}

psBMSCell13Voltage OBJECT-TYPE
	SYNTAX			INTEGER
	UNITS			"0.001V"
	MAX-ACCESS		read-only
	STATUS			current
	DESCRIPTION		"BMS cell 13 voltage in 0.001V."
	::= {psBMSEntry 27}

psBMSCell14Voltage OBJECT-TYPE
	SYNTAX			INTEGER
	UNITS			"0.001V"
	MAX-ACCESS		read-only
	STATUS			current
	DESCRIPTION		"BMS cell 14 voltage in 0.001V."
	::= {psBMSEntry 28}

psBMSCell15Voltage OBJECT-TYPE
	SYNTAX			INTEGER
	UNITS			"0.001V"
	MAX-ACCESS		read-only
	STATUS			current
	DESCRIPTION		"BMS cell 15 voltage in 0.001V."
	::= {psBMSEntry 29}    

psBMSCell16Voltage OBJECT-TYPE
	SYNTAX			INTEGER
	UNITS			"0.001V"
	MAX-ACCESS		read-only
	STATUS			current
	DESCRIPTION		"BMS cell 16 voltage in 0.001V."
	::= {psBMSEntry 30}


----------------------------------------------------------------------------

-- добавлены маски r4BatteryLiIonAlarm и r4BatteryBMSComFail (a1, a2, r1, r2, r3, r4)
-- добавлена ветка psBMS

END
